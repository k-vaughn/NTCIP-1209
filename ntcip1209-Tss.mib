-- To the extent that these materials are distributed by AASHTO / ITE / NEMA 
-- in the form of a Data Dictionary (DD) or Management Information Base 
-- (MIB), AASHTO / ITE / NEMA extend the following permission:

-- You may make or distribute unlimited copies, including derivative works, 
-- of the DD or MIB, including copies for commercial distribution, provided 
-- that:

-- a)	each copy you make or distribute includes the citation Derived from 
--    NTCIP 0000 [insert the standard number]. Copyright by AASHTO / ITE / 
--    NEMA. Used by permission.;
-- b)	the copies are not edited from the published version of this document. 

-- These materials are delivered AS IS without any warranties as to their 
-- use or performance.

-- AASHTO / ITE / NEMA and their suppliers do not warrant the performance or 
-- results you may obtain by using these materials. AASHTO / ITE / NEMA and 
-- their suppliers make no warranties, express or implied, as to 
-- noninfringement of third party rights, merchantability, or fitness for any
--  particular purpose. In no event will AASHTO / ITE / NEMA or their 
-- suppliers be liable to you or any third party for any claim or for any 
-- consequential, incidental or special damages, including any lost profits 
-- or lost savings, arising from your reproduction or use of these materials, 
-- even if an AASHTO / ITE / NEMA representative has been advised of the 
-- possibility of such damages.

-- Some states or jurisdictions do not allow the exclusion or limitation of 
-- incidental, consequential, or special damages, or the exclusion of implied 
-- warranties, so the above limitations may not apply to a given user.

-- Use of these materials does not constitute an endorsement or affiliation 
-- by or between AASHTO, ITE, or NEMA and the user, the users company, or 
-- the products and services of the users company.

-- If the user is unwilling to accept the foregoing restrictions, he or she 
--should immediately return these materials.

-- 5.1 TRANSPORTATION SENSOR SYSTEM OBJECTS 
NTCIP1209-Tss  DEFINITIONS::= BEGIN
IMPORTS
MODULE-IDENTITY, OBJECT-IDENTITY, OBJECT-TYPE, Integer32, Unsigned32
                                               FROM SNMPv2-SMI
                                                 -- RFC 2578  
TEXTUAL-CONVENTION, TruthValue
                                               FROM SNMPv2-TC
                                                 -- RFC 2579
OBJECT-GROUP
                                               FROM SNMPv2-CONF
                                                 -- RFC 2580
SnmpAdminString
                                               FROM SNMP-FRAMEWORK-MIB
                                                 -- RFC 3411
ITSBitmap, ITSUByteString, ITSUnsigned8, ITSTimeStamp 
                                               FROM ISO26048-1-Global-TC
devices, NtcipOctetBitmap8
                                               FROM NTCIP8004-Transportation;

tss MODULE-IDENTITY
  LAST-UPDATED "202401230500Z"
  ORGANIZATION "NTCIP TSS WG"
  CONTACT-INFO
   "name: NTCIP Coordinator
    email: ntcip@nema.org
    postal: National Electrical Manufacturers Association
            1300 North 17th Street, Suite 1752
            Rosslyn, Virginia 22209-3801"
  DESCRIPTION
  "<Definition> This MIB defines the object definitions for Transportation 
    sensor systems (TSS)
  <Object Identifier> 1.3.6.1.4.1.1206.4.2.4"

  REVISION "202401230500Z"
  DESCRIPTION
    "NTCIP 1209 v03 - Upgraded to SMIv2 format and incorporated objects from
      the ISO 20684 series into design."
  REVISION "201405010500Z"
  DESCRIPTION
    "NTCIP 1209 v02 - Corrections based on user experience and addition of 
      systems engineering content to the standard."
  REVISION "200511010500Z"
  DESCRIPTION
    "NTCIP 1209:2005 (v01) - Original version."
  ::= { devices 4 }

-- Additional textual conventions for v01 and v02 that have since been 
-- deprecated.
TssBitmap64  ::= TEXTUAL-CONVENTION
  DISPLAY-HINT "1x "
  STATUS       deprecated
  DESCRIPTION "An 8-octet bit string whose bit ordering proved confusing to 
    implementers."
  SYNTAX  OCTET STRING (SIZE (8))

TssBitmap96  ::= TEXTUAL-CONVENTION
  DISPLAY-HINT "1x "
  STATUS       deprecated
  DESCRIPTION "An 12-octet bit string whose bit ordering proved confusing to 
    implementers."
  SYNTAX  OCTET STRING (SIZE (12))

TssBitmap256  ::= TEXTUAL-CONVENTION
  DISPLAY-HINT "1x "
  STATUS       deprecated
  DESCRIPTION "An 32-octet bit string whose bit ordering proved confusing to 
    implementers."
  SYNTAX  OCTET STRING (SIZE (32))
-- 5.2 SENSOR CONFIGURATION AND CAPABILITY OBJECTS
tssSystemSetup OBJECT-IDENTITY 
STATUS  current
DESCRIPTION
"This node is an identifier used to group all objects for TSS sensor 
configurations that are common to all TSS. 
<Object Identifier> 1.3.6.1.4.1.1206.4.2.4.1"
::= { tss 1 }

-- 5.2.1 Sensor Reset, Resynchronization, and Diagnostics
sensorSystemReset  OBJECT-TYPE
SYNTAX  INTEGER {
                  restart (1), -- deprecated
                  reinitializeUserSettings (2),
                  restoreFactoryDefaults (3),
                  retune (4),
                  resyncSamplingPeriods (5),
                  shortDiagnostics (6),
                  fullDiagnostics (7),
                  executePendingConfiguration (8),
                  abortPendingConfiguration (9),
                  validatePendingConfiguration (10),
                  noResetInProgress (11)}
MAX-ACCESS  read-write
STATUS  current
DESCRIPTION
"<Definition> A software interface to initiate a reset of various functions of
the TSS. Upon receiving a request to set this object, the TSS shall follow the
state transition rules defined in Section 4.3.1. Upon completing the processing
of a successful set, the TSS shall transition the value of this object back to
'noResetInProgress'.
The reset values are described as follows:
      restart(1) - This command shall cause the unit to enter restart state
      and go through a complete shut-down and start-up process, causing a
      reset and initialization of the number of seconds since most recent
      TSS initialization to a value of zero.
      reinitializeUserSettings(2) - This command shall cause the unit to 
      flush all memory and reinitialize all settings to their user-defined 
      default values, and reset and initialize the number of seconds since 
      most recent TSS initialization to a value of zero.
      restoreFactoryDefaults(3) - This command shall cause the unit to flush
      all memory, restore all settings to their factory default values, and
      reset and initialize the number of seconds since most recent TSS
      initialization to a value of zero.
      retune(4) - This command recalibrates unit background settings for all
      zones without resetting or flushing of any collected data.
      resyncSamplingPeriods(5) - This command shall cause the unit to
      synchronize all startup sampling period clocks within one (1) second of
      receiving the command and a reset and initialize of the number of
      seconds since most recent TSS initialization to a value of zero.
      shortDiagnostics(6) - This command shall cause the unit to go through
      an abbreviated vendor-specific diagnostic routine which may be the same
      as full diagnostics for some vendors.
      fullDiagnostics(7) - This command shall cause the unit to go through
      a complete vendor-specific diagnostic routine which may be the same as
      short diagnostics for some vendors, causing a reset and initialization
      of the number of seconds since most recent TSS initialization to a
      value of zero.
      executePendingConfiguration(8) - The behavior of this command is
      dependent upon type of configuration file uploaded and is manufacturer-
      specific. Execution may result in a system reboot, reinitialization,
      and loss of historical data.
      abortPendingConfiguration(9) - This command shall cause the TSS
      to cancel the currently pending configuration changes.
      validatePendingConfiguration(10) - This command is used to check the
      configuration to ensure that it is a valid configuration file.
      noResetInProgress(11) - No command is in-progress. The TSS shall 
      automatically transition this object back to this state upon 
      completion of the requested command. This value is read-only.
<Parameter Type> Control
<Informative> The value 'restart' (1) was deprecated in v03 in favor of using 
  fdCtrlReset. If the value 1 is supported, it shall act the same as setting 
  fdCtrlReset to 'true'.
<Object Identifier> 1.3.6.1.4.1.1206.4.2.4.1.1"
::= { tssSystemSetup 1 }

-- 5.2.2 Sensor System Status
sensorSystemStatus  OBJECT-TYPE
SYNTAX  INTEGER {
                 other (1),
                 oK (2),
                 initializing (3),
                 pendingConfigurationChange (4),
                 validatingPendingConfiguration (5),
                 diagError (6),
                 activeConfigError (7),
                 pendingConfigError (8) }
MAX-ACCESS  read-only
STATUS  current
DESCRIPTION
"<Definition> This data element provides an indication of the overall sensor
system status, as follows:
      other(1) - Indicates the presence of a hardware or software status that
      is not described by any other valid value of this object.
      oK(2) - Indicates that the unit is operating normally with no known
      hardware or software faults, with no implications about data.
      initializing(3) - Indicates that the unit has not encountered any 
      fault, but is not ready for detection.
      pendingConfigurationChange(4) - Indicates there is a new configuration
      that is ready to be implemented in the TSS (i.e., by setting 
      sensorSystemReset to a value of executePendingConfiguration).
      validatingPendingConfiguration (5) - Indicates that the TSS is
      checking that the downloaded file is a valid configuration file.
      diagError (6) - Indicates that a hardware malfunction has been
      identified.
      activeConfigError (7) - Indicates that the current configuration being
      used in the TSS is invalid.
      pendingConfigError (8) - Indicates that the pending configuration file
      is invalid.
<Parameter Type> Status
<Object Identifier> 1.3.6.1.4.1.1206.4.2.4.1.2"
::= { tssSystemSetup 2 }

-- 5.2.3 Sensor System Occupancy Type
sensorSystemOccupancyType OBJECT-TYPE
SYNTAX  INTEGER {
                  normalizedOtherOccupancy (1),
                  nonNormalizedOccupancy (2),
                  zoneOccupancy (3),
                  normalizedSixFootLoopOccupancy (4),
                  normalizedTwoMeterLoopOccupancy (5),
                  normalizedPointOccupancy (6)}
MAX-ACCESS  read-write
STATUS  current
DESCRIPTION 
"<Definition> Indicates how to interpret the occupancy data of this TSS.
      normalizedOtherOccupancy(1) - Occupancy is normalized to other
      specific criteria that are not defined by other enumerated entries of
      this data element. Use of this enumeration should be done carefully
      as it could effect interoperability of equipment.
      nonNormalizedOccupancy(2) - Occupancy is presented as non-normalized or
      raw occupancy data.
      zoneOccupancy(3) - Occupancy is presented for a given zone.
      normalizedSixFootLoopOccupancy(4) - Occupancy is normalized to a 6-foot
      by 6-foot loop.
      normalizedTwoMeterLoopOccupancy(5) - Occupancy is normalized to a 2-
      meter by 2-meter loop.
      normalizedPointOccupancy(6) - Occupancy is normalized to a point.
<Parameter Type> Configuration
<Object Identifier> 1.3.6.1.4.1.1206.4.2.4.1.3"
::= { tssSystemSetup 3 }

-- 5.2.4 Maximum Number of Sensor Zones Parameter
maxSensorZones OBJECT-TYPE
SYNTAX  Integer32 (1..255)
MAX-ACCESS  read-only
STATUS  current
DESCRIPTION 
"<Definition> Indicates the maximum number of sensor zones supported by this
TSS.
<Parameter Type> Status 
<Object Identifier> 1.3.6.1.4.1.1206.4.2.4.1.4"
::= { tssSystemSetup 4 }

-- 5.2.5 Sensor Zone Table
sensorZoneTable  OBJECT-TYPE
SYNTAX  SEQUENCE OF SensorZoneEntry
MAX-ACCESS  not-accessible
STATUS  current
DESCRIPTION 
"<Definition> A table containing sensor zone unit parameters. The number of
rows in this table is equal to the maxSensorZones data element. Table rows are
set by the manufacturer, and row creation/deletion is not supported.
<TableType> static
<Object Identifier> 1.3.6.1.4.1.1206.4.2.4.1.5"
::= { tssSystemSetup 5}

sensorZoneEntry  OBJECT-TYPE
SYNTAX  SensorZoneEntry
MAX-ACCESS  not-accessible
STATUS  current
DESCRIPTION 
"<Definition> Table for sensor zone parameters.
<Object Identifier> 1.3.6.1.4.1.1206.4.2.4.1.5.1"

INDEX { sensorZoneNumber }
::= { sensorZoneTable 1 }

SensorZoneEntry ::= SEQUENCE {
      sensorZoneNumber                    Integer32,
      sensorZoneOptions                   ITSBitmap,
      sensorZoneOptionsStatus             ITSBitmap,
      sensorZoneSamplePeriod              Integer32,
      sensorZoneLabel                     SnmpAdminString,
      sensorZoneAndOperator               ITSUByteString,
      sensorZoneOrOperator                ITSUByteString,
      sensorZonePairedZone                Integer32,
      sensorZonePairedZoneOptions         ITSBitmap,
      sensorZonePairedZoneSpacing         Integer32,
      sensorZoneSpeedCorrectionFactor     Integer32,
      sensorZoneAvgVehicleLength          Integer32,
      sensorZoneLength                    Integer32,
      sensorZoneStatus                    INTEGER,
      sensorZoneNoActivityFaultTime       Integer32,
      sensorZoneMaxPresenceFaultTime      Integer32,
      sensorZoneErraticCountsFaultTime    Integer32,
      sensorZoneErraticCountsThreshold    Integer32,
      sensorZoneTechnology                INTEGER }

-- 5.2.5.1 Sensor Zone Number
sensorZoneNumber  OBJECT-TYPE
SYNTAX  Integer32 (1..255)
MAX-ACCESS  read-only
STATUS  current
DESCRIPTION 
"<Definition> The numerical label or number of the sensor zone. This value
shall not exceed the maxSensorZones data element value. sensorZoneNumber is
used as an index for various data element tables.
<Parameter Type> Status 
<Object Identifier> 1.3.6.1.4.1.1206.4.2.4.1.5.1.1"
::= { sensorZoneEntry 1 }

-- 5.2.5.2 Sensor Zone Options
sensorZoneOptions  OBJECT-TYPE
SYNTAX   ITSBitmap (SIZE(1))
MAX-ACCESS  read-write
STATUS  current
DESCRIPTION 
"<Definition> A bit-mapped value indicating whether each identified option is
configured to be enabled. A non-configured system shall default all options to
disabled. Any attempt to set a value that sets a reserved bit shall be
rejected.
<Format>
Bit 0      Enable this sensor zone
Bits 1..7  Reserved
<Parameter Type> Configuration 
<Informative> v03 updated the syntax and bit numbering to be consistent with
SNMP conventions but the encoded representation is identical to what was
defined in v02 (i.e., the data is encoded in the high-order bits). See NTCIP
8004 v03, 4.5.3 for more information about the encoding of bitstrings.
<Object Identifier> 1.3.6.1.4.1.1206.4.2.4.1.5.1.2"
::= { sensorZoneEntry 2 }

-- 5.2.5.3 Sensor Zone Options Status
sensorZoneOptionsStatus  OBJECT-TYPE
SYNTAX  ITSBitmap (SIZE(1))
MAX-ACCESS  read-only
STATUS  current
DESCRIPTION 
"<Definition> A bit-mapped value indicating the status of whether each
identified option is enabled. This value can be different than
sensorZoneOptions if the sensor has automatically disabled a zone. Example: The
TSS is a camera that has Pan/Tilt/Zoom control and the camera is temporarily
moved for a surveillance operation. For each zone associated with this camera,
Bit 0 of sensorZoneOptionsStatus would remain or become 'diabled' (0) while Bit
0 of sensorZoneOptions would not change. Upon returning the camera to its
sensing position, the TSS would attempt to apply the state requested by
sensorZoneOptions (assuming all conditions are met for the camera). 
<Format>
Bit 0     Status of this sensor zone;
Bits 1..7 Reserved
<Parameter Type> Status 
<Informative> v03 updated the syntax and bit numbering to be consistent with
SNMP conventions but the encoded representation is identical to what was
defined in v02 (i.e., the data is encoded in the high-order bits). See NTCIP
8004 v03, 4.5.3 for more information about the encoding of bitstrings.
<Object Identifier> 1.3.6.1.4.1.1206.4.2.4.1.5.1.3"
::= { sensorZoneEntry 3 }

-- 5.2.5.4 Sensor Zone Sample Period Parameter
sensorZoneSamplePeriod  OBJECT-TYPE
SYNTAX  Integer32 (0..65535)
UNITS   "seconds"
MAX-ACCESS  read-write
STATUS  current
DESCRIPTION 
"<Definition> Duration of the sample period in seconds for the sensor zone over
which time data is collected. Sample period durations from 0 to 3600 are
available for use. Values from 3601 to 65535 are reserved for future use. A
sampling period of zero (0) means that data is not being collected, while the
sensor zone may continue to be enabled.
<Parameter Type> Configuration 
<Object Identifier> 1.3.6.1.4.1.1206.4.2.4.1.5.1.4"
DEFVAL { 0 }
::= { sensorZoneEntry 4 }

-- 5.2.5.5 Sensor Zone Label
sensorZoneLabel  OBJECT-TYPE
SYNTAX     SnmpAdminString
MAX-ACCESS read-write
STATUS     current
DESCRIPTION 
"<Definition> A text string used to describe the TSS sensor zone. A maximum
string length of less than 255 may be supported.
<Parameter Type> Configuration 
<Informative> Prior to v03, the syntax contained a typo implying that labels
shorter than 8 octets were not allowed; as such, such values might be rejected
by some implementations.
<Object Identifier> 1.3.6.1.4.1.1206.4.2.4.1.5.1.5"
::= { sensorZoneEntry 5 }

-- 5.2.5.6 Sensor Zone Boolean AND Operator
sensorZoneAndOperator OBJECT-TYPE
SYNTAX  ITSUByteString (SIZE (8))
MAX-ACCESS  read-write
STATUS  current
DESCRIPTION
"<Definition> This data element identifies up to eight (8) unique zones that
can be sequentially combined with a Boolean AND command to provide an input to
this zone, as follows:
<Format>
Each octet indicates the sensorZoneNumber of a sensor zone input that is to be
combined with the input for this zone using Boolean AND logic. An octet with a
value of zero (0) indicates that no sensor zone is assigned for that entry.

Boolean AND combinations are processed before Boolean OR combinations. When
read, this object returns last value written.
<Parameter Type> Configuration 
<Informative> v03 updated the syntax but the encoded representation is
identical to what was defined in v02.
<Object Identifier> 1.3.6.1.4.1.1206.4.2.4.1.5.1.6"
::= { sensorZoneEntry 6 }

-- 5.2.5.7 Sensor Zone Boolean OR Operator
sensorZoneOrOperator OBJECT-TYPE
SYNTAX  ITSUByteString (SIZE (8))
MAX-ACCESS  read-write
STATUS  current
DESCRIPTION
"<Definition> This data element identifies up to eight (8) unique zones that
can be sequentially combined with a Boolean OR command to provide an input to
this zone, as follows:
<Format>
Each octet indicates the sensorZoneNumber of a sensor zone input that is to be
combined with the input for this zone using Boolean OR logic. An octet with a
value of zero (0) indicates that no sensor zone is assigned for that entry.

Boolean AND combinations are processed before Boolean OR combinations. When
read, this object returns last value written.
<Parameter Type> Configuration 
<Informative> v03 updated the syntax but the encoded representation is
identical to what was defined in v02.
<Object Identifier> 1.3.6.1.4.1.1206.4.2.4.1.5.1.7"
::= { sensorZoneEntry 7 }

-- 5.2.5.8 Sensor Zone Paired Zone
sensorZonePairedZone  OBJECT-TYPE
SYNTAX  Integer32 (0..255)
MAX-ACCESS  read-write
STATUS  current
DESCRIPTION
"<Definition> This indicates the sensorZoneNumber of a paired zone that
provides additional information to the current zone for features that require a
sequenced second zone to determine direction of travel or time of travel (e.g.,
speed trap, wrong way, etc.)
<Parameter Type> Configuration 
<Object Identifier> 1.3.6.1.4.1.1206.4.2.4.1.5.1.8"
::= { sensorZoneEntry 8 }

-- 5.2.5.9 Sensor Zone Paired Zone Options
sensorZonePairedZoneOptions  OBJECT-TYPE
SYNTAX  ITSBitmap (SIZE (1))
MAX-ACCESS  read-write
STATUS  current
DESCRIPTION
"<Definition> A bit-mapped value as defined below for indicating the status of
the options for a paired zone.
<Format>
Bit 7  Zone Placement: ON indicates that this is the leading zone of the pair 
                      OFF indicates that this is a trailing zone of the pair.
Bit 6  Single Zone Speed Mode: If there is an error on either paired zone: 
            OFF: speed is calculated using a manufacturer specific algorithm
            ON: speed is calculated using the formula:
            (sensorZoneAvgVehicleLength + sensorZoneLength) / Detect Time (s)
Bit 5..0 Reserved 
<Informative> v03 updated the syntax and bit numbering to be consistent with
SNMP conventions but the encoded representation is identical to what was
defined in v02 (i.e., the data is encoded in the high-order bits). See NTCIP
8004 v03, 4.5.3 for more information about the encoding of bitstrings.
<Parameter Type> Configuration 
<Object Identifier> 1.3.6.1.4.1.1206.4.2.4.1.5.1.9"
::= { sensorZoneEntry 9 }

-- 5.2.5.10 Sensor Zone Paired Zone Spacing
sensorZonePairedZoneSpacing  OBJECT-TYPE
SYNTAX  Integer32 (1..255)
UNITS   "centimeters"
MAX-ACCESS  read-write
STATUS  current
DESCRIPTION
"<Definition> This parameter allows the user to set the spacing between paired
zones for use in calculating vehicle speeds. This parameter is usually measured
from the leading edge of one zone to the leading edge of the paired zone. 
<Parameter Type> Configuration 
<Object Identifier> 1.3.6.1.4.1.1206.4.2.4.1.5.1.10"
::= { sensorZoneEntry 10 }

-- 5.2.5.11 Sensor Zone Speed Correction Factor
sensorZoneSpeedCorrectionFactor  OBJECT-TYPE
SYNTAX  Integer32 (1..20000)
UNITS   "one-thousandth of a percent"
MAX-ACCESS  read-write
STATUS  current
DESCRIPTION
"<Definition> This is a percent multiplier for speed calculations within the
TSS that is used to fine tune the accuracy of the reported speed. A setting of
1000 would be a multiplier of 1.000.
<Parameter Type> Configuration 
<Object Identifier> 1.3.6.1.4.1.1206.4.2.4.1.5.1.11"
::= { sensorZoneEntry 11 }

-- 5.2.5.12 Sensor Zone Average Vehicle Length
sensorZoneAvgVehicleLength  OBJECT-TYPE
SYNTAX  Integer32 (1..4000)
UNITS   "centimeters"
MAX-ACCESS  read-write
STATUS  current
DESCRIPTION
"<Definition> This parameter allows the user to set the average vehicle length
for use in determining speed and classification. This allows for a range of
lengths between 0.01 meters to 40 meters in length.
<Parameter Type> Configuration 
<Object Identifier> 1.3.6.1.4.1.1206.4.2.4.1.5.1.12"
::= { sensorZoneEntry 12}

-- 5.2.5.13 Sensor Zone Length Parameter
sensorZoneLength  OBJECT-TYPE
SYNTAX  Integer32 (1..4000 | 65535)
UNITS   "centimeters"
MAX-ACCESS  read-write
STATUS  current
DESCRIPTION
"<Definition> This parameter allows the user to set the length of the sensor
zone. The value of 65535 shall be returned to represent no zone length set.
This allows for a range of lengths between 0.01 meters to 40 meters in length.
<Parameter Type> Configuration 
<Object Identifier> 1.3.6.1.4.1.1206.4.2.4.1.5.1.13"
::= { sensorZoneEntry 13 }

-- 5.2.5.14 Sensor Zone Status
sensorZoneStatus  OBJECT-TYPE
SYNTAX  INTEGER {
                 other (1),
                 oK (2),
                 initializing (3),
                 noActivity (4),
                 maxPresence (5),
                 configurationError (6),
                 erraticCounts (7),
                 disabled (8),
                 overrideActive (9),
                 sensorFailure (10),
                 inputDataIntegrity (11),
                 poorContrast (12),
                 detectionAutoSuspended (13),
                 pairedZoneFault (14) }
MAX-ACCESS  read-only
STATUS  current
DESCRIPTION
"<Definition> Detailed status returned as result of diagnostics, as follows:
      Value       Meaning
      other(1) - Indicates an error has occurred within the TSS for which
      there is no defined definition within this data element.
      oK(2) - Indicates no other status values apply.
      initializing(3) - Indicates an initialization or diagnostics procedure
      is in-progress.
      noActivity(4) - Indicates no activity condition.
      maxPresence(5) - Indicates max presence condition.
      configurationError(6) - Indicates an error within the TSS
      configuration setup.
      erraticCounts(7 )- Indicates erratic counts.
      disabled(8) - Indicates that the zone is disabled.
      overrideActive(9) - Indicates an override is active.
      sensorFailure(10) - Indicates a sensing element failure.
      inputDataIntegrity(11) - Indicates input values are not sufficient to
      determine detector data accurately (e.g., bad communications, invalid
      video for machine vision)
      poorContrast(12) - Indicates insufficient contrast error condition.
      detectionAutoSuspended(13) - Indicates that the detection zone was
      automatically disabled by the TSS (e.g., camera is on a PTZ and
      was moved).
      pairedZoneFault(14) - Indicates that there was no problem with this
      zone, but a zone that it is paired with had a fault. This may affect
      the accuracy of data reported by this zone.
If a condition occurs during the sample period, then that state remains for the
duration of that sample period. If multiple conditions occur during a sample
period, the last reported condition, other than OK, is retained.
<Parameter Type> Status 
<Object Identifier> 1.3.6.1.4.1.1206.4.2.4.1.5.1.14"
::= { sensorZoneEntry 14 }

-- 5.2.5.15 Sensor Zone No Activity Fault Time
sensorZoneNoActivityFaultTime  OBJECT-TYPE
SYNTAX  Integer32 (0..65535)
UNITS   "seconds"
MAX-ACCESS  read-write
STATUS  current
DESCRIPTION
"<Definition> Time period in seconds for the sensor zone during which, if there
is no activity for the zone, a No Activity status is generated for the zone. A
no activity fault time of zero (0) means that a no activity status cannot be
generated for this sensor zone.
<Parameter Type> Configuration 
<Object Identifier> 1.3.6.1.4.1.1206.4.2.4.1.5.1.15"
DEFVAL { 0 }
::= { sensorZoneEntry 15 }

-- 5.2.5.16 Sensor Zone Max Presence Fault Time
sensorZoneMaxPresenceFaultTime  OBJECT-TYPE
SYNTAX  Integer32 (0..65535)
UNITS   "seconds"
MAX-ACCESS  read-write
STATUS  current
DESCRIPTION
"<Definition> Time period in seconds for the sensor zone during which, if there
is constant activity for the zone, a Max Presence status is generated for the
zone. A max presence fault time of zero (0) means that a max presence status
cannot be generated for this sensor zone.
<Parameter Type> Configuration 
<Object Identifier> 1.3.6.1.4.1.1206.4.2.4.1.5.1.16"
DEFVAL { 0 }
::= { sensorZoneEntry 16 }

-- 5.2.5.17 Sensor Zone Erratic Counts Fault Time
sensorZoneErraticCountsFaultTime  OBJECT-TYPE
SYNTAX  Integer32 (0..65535)
UNITS   "seconds"
MAX-ACCESS  read-write
STATUS  current
DESCRIPTION
"<Definition> Time period in seconds for the sensor zone during which, if the
Erratic Counts Threshold is created for the zone, an Erratic Counts status is
generated for the zone. An erratic counts fault time of zero (0) means that an
erratic counts status cannot be generated for this sensor zone.
<Parameter Type> Configuration 
<Object Identifier> 1.3.6.1.4.1.1206.4.2.4.1.5.1.17"
DEFVAL { 0 }
::= { sensorZoneEntry 17 }

-- 5.2.5.18 Sensor Zone Erratic Counts Threshold
sensorZoneErraticCountsThreshold  OBJECT-TYPE
SYNTAX  Integer32 (0..65535)
UNITS   "actuations"
MAX-ACCESS  read-write
STATUS  current
DESCRIPTION
"<Definition> The number of actuations that if met or exceeded within the
Erratic Counts Fault Time, an Erratic Counts status is generated for the zone.
An erratic counts threshold of zero (0) means that an erratic counts status
cannot be generated for this sensor zone.
<Parameter Type> Configuration 
<Object Identifier> 1.3.6.1.4.1.1206.4.2.4.1.5.1.18"
DEFVAL { 0 }
::= { sensorZoneEntry 18 }

-- 5.2.5.19 Sensor Zone Technology
sensorZoneTechnology  OBJECT-TYPE
SYNTAX  INTEGER {
                 other (1),
                 inductiveLoop (2),
                 machineVision (3) }
MAX-ACCESS  read-only
STATUS  current
DESCRIPTION 
"<Definition> Indicates the sensor technology used by this sensor zone.
      other(1) - Any technology that is not currently covered by this
      standard. (e.g., microwave detectors)
      inductive loop (2) - A physical detector of coiled wire that is
      embedded in the driving surface that senses changes in magnetic
      field as vehicles pass over. 
      machine vision (3) - A non intrusive detection methodology
      where in a video image of the driving surface is processed to
      determine the passage of a vehicle.
<Parameter Type> Status 
<Object Identifier> 1.3.6.1.4.1.1206.4.2.4.1.5.1.19"
::= { sensorZoneEntry 19 }

-- 5.2.6 Clock Available
clockAvailable OBJECT-TYPE
SYNTAX  INTEGER {
                 clockYes (1),
                 clockNo (2) }
MAX-ACCESS  read-only
STATUS  deprecated
DESCRIPTION 
"<Definition> Indicates availability of a real time clock within the TSS so
that time can be referenced to CTime.
      clockYes(1) - A real time clock is provided within the TSS,
      conformant with the applicable requirements for managing time in NTCIP
1201 v03, and time is referenced to actual local time within the device.
      clockNo(2) - A real time clock is not provided within the TSS and
      time is expressed in the number of seconds since most recent TSS
      initialization.
<Parameter Type> Status 
<Withdrawn>
<Informative> This object was deprecated in NTCIP 1209 v03 due to the migration
from NTCIP 1201 v03 to ISO 26048-1. The functionality of this object can be
achieved in the new design by checking on the existance of fdClockLocalTime.
<Object Identifier> 1.3.6.1.4.1.1206.4.2.4.1.6"
::= { tssSystemSetup 6 }

-- 5.2.7 Sensor Technology
sensorTechnology  OBJECT-TYPE
SYNTAX  INTEGER {
                 other (1),
                 inductiveLoop (2),
                 machineVision (3) }
MAX-ACCESS  read-only
STATUS  deprecated
DESCRIPTION 
"<Definition> Indicates the sensor technology used by this TSS.
      other(1) - Any TSS that is not currently covered by this
      standard. (e.g., microwave detectors)
      inductive loop (2) - A physical detector of coiled wire that is
      embedded in the driving surface that senses changes in magnetic
      field as vehicles pass over. 
      machine vision (3) - A non intrusive detection methodology
      where in a video image of the driving surface is processed to
      determine the passage of a vehicle.
<Parameter Type> Status 
<Superseded by> sensorZoneTechnology
<Object Identifier> 1.3.6.1.4.1.1206.4.2.4.1.7"
::= { tssSystemSetup 7 }

-- 5.2.8 Maximum Sample Data Entries
maxSampleDataEntries  OBJECT-TYPE
SYNTAX  Integer32 (1..4)
UNITS   "entries"
MAX-ACCESS  read-only
STATUS  current
DESCRIPTION
"<Definition> Indicates the maximum number of historical data entries per zone
supported by the TSS.
<Parameter Type> Status 
<Object Identifier> 1.3.6.1.4.1.1206.4.2.4.1.8"
::= { tssSystemSetup 8 }

-- 5.2.9 Maximum Number of Characters
maxNumberOfCharacters  OBJECT-TYPE
SYNTAX  Integer32 (8..255)
UNITS   "octets"
MAX-ACCESS  read-only
STATUS  current
DESCRIPTION
"<Definition> The maximum number of octets in any identifier label that the TSS
supports. 
<Parameter Type> Status 
<Informative> If the label uses only NVT-ASCII characters, this is equal to the
number of characters.
<Object Identifier> 1.3.6.1.4.1.1206.4.2.4.1.9"
::= { tssSystemSetup 9 } 

-- 5.2.10 Functional Capabilities
functionalCapabilities  OBJECT-TYPE
SYNTAX  ITSBitmap (SIZE (1))
MAX-ACCESS  read-only
STATUS  current
DESCRIPTION
"<Definition> A bit-mapped value as defined below for identifying the
functional capabilities of the TSS.
<Format>
bit 7       Sampling Features
bit 6       Timing Features
bit 5       Speed Features
bits  0..4  Reserved
<Parameter Type> Status 
<Informative> v03 updated the syntax and bit numbering to be consistent with
SNMP conventions but the encoded representation is identical to what was
defined in v02 (i.e., the data is encoded in the high-order bits). See NTCIP
8004 v03, 4.5.3 for more information about the encoding of bitstrings.
<Object Identifier> 1.3.6.1.4.1.1206.4.2.4.1.10"
::= { tssSystemSetup 10 }

-- 5.2.11 External Arming Inputs
externalArmingInputs  OBJECT-TYPE
SYNTAX  TssBitmap64
MAX-ACCESS  read-write
STATUS  deprecated
DESCRIPTION
"<Definition> This allows other devices to modify the states of the Arming
Input Bits used by the TSS. There are separate clears and sets so that multiple
TSSs could maintain the states of individual Arming Input Bits. It is
envisioned that the first 24 bits would correspond to the Greens, Yellows, and
Reds of phases 1 through 8 from the traffic signal controller. The last 8 bits
would be used for other phases, overlaps, or special functions. If the Arming
Pin inputs are DC then a low input is an ON and a high input is an OFF. If the
Arming Pin inputs are AC then a low input is an OFF and a high input is an ON.
An attempt to write to this object with a value that has an Arming Input
configured to both Clear and Set (e.g., Bit 0 of Byte 1 and Byte 5 are set)
shall cause the Arming Input bit to clear (i.e, clear overrides set). A read of
this object shall indicate '1' for the Clear bit and a '0' for the Set bit for
each Arming Input that is OFF and shall indicate '0' for the Clear bit and a
'1' for the Set bit for each Arming Input that is ON. 
<Format>
byte 1      Bit 0 = Clear Arming Input bit 1,
            Bit 1 = Clear Arming Input bit 2,
            Bit 2 = Clear Arming Input bit 3,
            Bit 3 = Clear Arming Input bit 4,
            Bit 4 = Clear Arming Input bit 5,
            Bit 5 = Clear Arming Input bit 6,
            Bit 6 = Clear Arming Input bit 7,
            Bit 7 = Clear Arming Input bit 8,
byte 2      Bit 0 = Clear Arming Input bit 9,
            Bit 1 = Clear Arming Input bit 10,
            Bit 2 = Clear Arming Input bit 11,
            Bit 3 = Clear Arming Input bit 12,
            Bit 4 = Clear Arming Input bit 13,
            Bit 5 = Clear Arming Input bit 14,
            Bit 6 = Clear Arming Input bit 15,
            Bit 7 = Clear Arming Input bit 16,
byte 3      Bit 0 = Clear Arming Input bit 17,
            Bit 1 = Clear Arming Input bit 18,
            Bit 2 = Clear Arming Input bit 19,
            Bit 3 = Clear Arming Input bit 20,
            Bit 4 = Clear Arming Input bit 21,
            Bit 5 = Clear Arming Input bit 22,
            Bit 6 = Clear Arming Input bit 23,
            Bit 7 = Clear Arming Input bit 24,
byte 4      Bit 0 = Clear Arming Input bit 25,
            Bit 1 = Clear Arming Input bit 26,
            Bit 2 = Clear Arming Input bit 27,
            Bit 3 = Clear Arming Input bit 28,
            Bit 4 = Clear Arming Input bit 29,
            Bit 5 = Clear Arming Input bit 30,
            Bit 6 = Clear Arming Input bit 31,
            Bit 7 = Clear Arming Input bit 32,
byte 5      Bit 0 = Set Arming Input bit 1,
            Bit 1 = Set Arming Input bit 2,
            Bit 2 = Set Arming Input bit 3,
            Bit 3 = Set Arming Input bit 4,
            Bit 4 = Set Arming Input bit 5,
            Bit 5 = Set Arming Input bit 6,
            Bit 6 = Set Arming Input bit 7,
            Bit 7 = Set Arming Input bit 8,
byte 6      Bit 0 = Set Arming Input bit 9,
            Bit 1 = Set Arming Input bit 10,
            Bit 2 = Set Arming Input bit 11,
            Bit 3 = Set Arming Input bit 12,
            Bit 4 = Set Arming Input bit 13,
            Bit 5 = Set Arming Input bit 14,
            Bit 6 = Set Arming Input bit 15,
            Bit 7 = Set Arming Input bit 16,
byte 7      Bit 0 = Set Arming Input bit 17,
            Bit 1 = Set Arming Input bit 18,
            Bit 2 = Set Arming Input bit 19,
            Bit 3 = Set Arming Input bit 20,
            Bit 4 = Set Arming Input bit 21,
            Bit 5 = Set Arming Input bit 22,
            Bit 6 = Set Arming Input bit 23,
            Bit 7 = Set Arming Input bit 24,
byte 8      Bit 0 = Set Arming Input bit 25,
            Bit 1 = Set Arming Input bit 26,
            Bit 2 = Set Arming Input bit 27,
            Bit 3 = Set Arming Input bit 28,
            Bit 4 = Set Arming Input bit 29,
            Bit 5 = Set Arming Input bit 30,
            Bit 6 = Set Arming Input bit 31,
            Bit 7 = Set Arming Input bit 32,
<Parameter Type> Configuration 
<Superseded by> externalArmingInputsV3 and externalArmingBitStatus  
<Informative> This object was deprecated due to confusion about the bit
ordering. See D.3.1 for more details.
<Object Identifier> 1.3.6.1.4.1.1206.4.2.4.1.11"
::= { tssSystemSetup 11 }

-- 5.2.12 Output Conditioning Table
-- The outputConditioningTable replaces the loopOutputConditioningTable that
-- is used in NTCIP 1209:2005 version v01.
outputConditioningTable  OBJECT-TYPE
SYNTAX  SEQUENCE OF OutputConditioningEntry
MAX-ACCESS  not-accessible
STATUS  current
DESCRIPTION
"<Definition> Each table row contains objects for configuring detector sensor
zone outputs. The number of rows in this table is equal to maxSensorZones.
Table rows are set by the manufacturer, and row creation/deletion is not
supported.
<TableType> static
<Object Identifier 1.3.6.1.4.1.1206.4.2.4.1.12"
::= { tssSystemSetup 12 }

outputConditioningEntry OBJECT-TYPE
SYNTAX  OutputConditioningEntry
MAX-ACCESS  not-accessible
STATUS  current
DESCRIPTION 
"<Definition> Each table row contains inductive loop detector sensor zone
output conditioning parameters. 
<Object Identifier> 1.3.6.1.4.1.1206.4.2.4.1.12.1"

INDEX { sensorZoneNumber }
::= { outputConditioningTable 1 }

OutputConditioningEntry ::= SEQUENCE {
      sensorZoneOutputMode             INTEGER,
      sensorZoneMaxPresenceTime        Integer32,
      sensorZoneOutputDelayTime        Integer32,
      sensorZoneOutputDelayMode        INTEGER,
      sensorZoneOutputDelayEnables     TssBitmap96,
      sensorZoneOutputExtendTime       Integer32,
      sensorZoneOutputExtendMode       INTEGER,
      sensorZoneOutputExtendEnables    TssBitmap96,
      sensorZoneOutputSequenced        Integer32 }

-- 5.2.12.1 Zone Output Mode
sensorZoneOutputMode  OBJECT-TYPE
SYNTAX  INTEGER {
                 other (1),
                 pulse (2),
                 presence (3),
                 invalid (255)  }
MAX-ACCESS  read-write
STATUS  current
DESCRIPTION 
"<Definition> This object sets the length of the output during a detect
condition. These detect outputs are described as follows:
      other(1) -  an output mode other than that defined in this list
      pulse(2) -  a pulse of 125ms (?25ms) is output when a vehicle is
      detected.
      presence(3) - the output lasts the duration of a detect condition
      or until the detector tunes out the detect signal.
      Invalid(255) -Something has invalid data.
<Parameter Type> Configuration 
<Object Identifier> 1.3.6.1.4.1.1206.4.2.4.1.12.1.1"
::= { outputConditioningEntry 1 }

-- 5.2.12.2 Zone Maximum Presence Time
sensorZoneMaxPresenceTime  OBJECT-TYPE
SYNTAX  Integer32 (0..65535)
UNITS   "seconds"
MAX-ACCESS  read-write
STATUS  current
DESCRIPTION 
"<Definition> This object sets the maximum time that the zone holds presence
before retuning. Values of 1 to 65534 seconds are available. A value of 0
disables this timer and prevents a sensor zone occupancy from being tuned out
at the end of a specific time. A value of 65,535 represents invalid data.
<Parameter Type> Configuration 
<Object Identifier> 1.3.6.1.4.1.1206.4.2.4.1.12.1.2"
::= { outputConditioningEntry 2 }

-- 5.2.12.3 Zone Output Delay Time
sensorZoneOutputDelayTime  OBJECT-TYPE
SYNTAX  Integer32 (0..65535)
UNITS   "deciseconds"
MAX-ACCESS  read-write
STATUS  current
DESCRIPTION 
"<Definition> The output for the zone is delayed from start of sensor zone
occupancy by the time specified (tenths of a second:  00.0 to 6553.5 sec). For
the output to actually switch, the sensor zone occupancy is required to be
continuous and still be present at the end of the delay time.
<Parameter Type> Configuration 
<Object Identifier> 1.3.6.1.4.1.1206.4.2.4.1.12.1.3"
REFERENCE
"NEMA TS2 Clause 3.5.5.5.4.c and 6.5.2.24.1"  
::= { outputConditioningEntry 3 }

-- 5.2.12.4 Zone Output Delay Mode Parameter
sensorZoneOutputDelayMode  OBJECT-TYPE
SYNTAX  INTEGER {
                 delayEnablesHaveNoEffect (1),
                 delayEnablesORedActive (2),
                 delayEnablesORedNotActive (3),
                 delayEnablesANDedActive (4),
                 delayEnablesANDedNotActive (5) }
MAX-ACCESS  read-write
STATUS  current
DESCRIPTION
"<Definition> This parameter determines if and how the delay enables are used
to modify the operation of the delay feature.
      delayEnablesHaveNoEffect(1) - The delay enables have no effect on the
      delay feature of the zone.
      delayEnablesORedActive(2) - If any of the delay enables are active the
      delay feature is active, else the delay feature is not active.
      delayEnablesORedNotActive(3) - If any of the delay enables are active
      the delay feature is not active, else the delay feature is active.
      delayEnablesANDedActive(4) - If all of the delay enables are active the
      delay feature is active, else the delay feature is not active.
      delayEnablesANDedNotActive(5) - If all of the delay enables are active
      the delay feature is not active, else the delay feature is active.
<Parameter Type> Configuration 
<Object Identifier> 1.3.6.1.4.1.1206.4.2.4.1.12.1.4"
::= { outputConditioningEntry 4 }

-- 5.2.12.5 Zone Output Delay Enables
sensorZoneOutputDelayEnables  OBJECT-TYPE
SYNTAX     TssBitmap96
MAX-ACCESS read-write
STATUS     deprecated
DESCRIPTION
"<Definition> This bit-mapped parameter identifies which Arming Pins, Arming
Input Bits, and which state for each are to be used as enables for the delay
feature. If the Arming Pin inputs are DC then a low input is an ON and a high
input is an OFF. If the Arming Pin inputs are AC then a low input is an OFF and
a high input is an ON.
<Format>
byte 1      Bit 0 = Arming Pin 1 OFF,
            Bit 1 = Arming Pin 2 OFF,
            Bit 2 = Arming Pin 3 OFF,
            Bit 3 = Arming Pin 4 OFF,
            Bit 4 = Arming Pin 5 OFF,
            Bit 5 = Arming Pin 6 OFF,
            Bit 6 = Arming Pin 7 OFF,
            Bit 7 = Arming Pin 8 OFF,
byte 2      Bit 0 = Arming Pin 9 OFF,
            Bit 1 = Arming Pin 10 OFF,
            Bit 2 = Arming Pin 11 OFF,
            Bit 3 = Arming Pin 12 OFF,
            Bit 4 = Arming Pin 13 OFF,
            Bit 5 = Arming Pin 14 OFF,
            Bit 6 = Arming Pin 15 OFF,
            Bit 7 = Arming Pin 16 OFF,
byte 3      Bit 0 = Arming Pin 1 ON,
            Bit 1 = Arming Pin 2 ON,
            Bit 2 = Arming Pin 3 ON,
            Bit 3 = Arming Pin 4 ON,
            Bit 4 = Arming Pin 5 ON,
            Bit 5 = Arming Pin 6 ON,
            Bit 6 = Arming Pin 7 ON,
            Bit 7 = Arming Pin 8 ON,
byte 4      Bit 0 = Arming Pin 9 ON,
            Bit 1 = Arming Pin 10 ON,
            Bit 2 = Arming Pin 11 ON,
            Bit 3 = Arming Pin 12 ON,
            Bit 4 = Arming Pin 13 ON,
            Bit 5 = Arming Pin 14 ON,
            Bit 6 = Arming Pin 15 ON,
            Bit 7 = Arming Pin 16 ON,
byte 5      Bit 0 = Arming Input bit 1 OFF,
            Bit 1 = Arming Input bit 2 OFF,
            Bit 2 = Arming Input bit 3 OFF,
            Bit 3 = Arming Input bit 4 OFF,
            Bit 4 = Arming Input bit 5 OFF,
            Bit 5 = Arming Input bit 6 OFF,
            Bit 6 = Arming Input bit 7 OFF,
            Bit 7 = Arming Input bit 8 OFF,
byte 6      Bit 0 = Arming Input bit 9 OFF,
            Bit 1 = Arming Input bit 10 OFF,
            Bit 2 = Arming Input bit 11 OFF,
            Bit 3 = Arming Input bit 12 OFF,
            Bit 4 = Arming Input bit 13 OFF,
            Bit 5 = Arming Input bit 14 OFF,
            Bit 6 = Arming Input bit 15 OFF,
            Bit 7 = Arming Input bit 16 OFF,
byte 7      Bit 0 = Arming Input bit 17 OFF,
            Bit 1 = Arming Input bit 18 OFF,
            Bit 2 = Arming Input bit 19 OFF,
            Bit 3 = Arming Input bit 20 OFF,
            Bit 4 = Arming Input bit 21 OFF,
            Bit 5 = Arming Input bit 22 OFF,
            Bit 6 = Arming Input bit 23 OFF,
            Bit 7 = Arming Input bit 24 OFF,
byte 8      Bit 0 = Arming Input bit 25 OFF,
            Bit 1 = Arming Input bit 26 OFF,
            Bit 2 = Arming Input bit 27 OFF,
            Bit 3 = Arming Input bit 28 OFF,
            Bit 4 = Arming Input bit 29 OFF,
            Bit 5 = Arming Input bit 30 OFF,
            Bit 6 = Arming Input bit 31 OFF,
            Bit 7 = Arming Input bit 32 OFF,
byte 9      Bit 0 = Arming Input bit 1 ON,
            Bit 1 = Arming Input bit 2 ON,
            Bit 2 = Arming Input bit 3 ON,
            Bit 3 = Arming Input bit 4 ON,
            Bit 4 = Arming Input bit 5 ON,
            Bit 5 = Arming Input bit 6 ON,
            Bit 6 = Arming Input bit 7 ON,
            Bit 7 = Arming Input bit 8 ON,
byte 10     Bit 0 = Arming Input bit 9 ON,
            Bit 1 = Arming Input bit 10 ON,
            Bit 2 = Arming Input bit 11 ON,
            Bit 3 = Arming Input bit 12 ON,
            Bit 4 = Arming Input bit 13 ON,
            Bit 5 = Arming Input bit 14 ON,
            Bit 6 = Arming Input bit 15 ON,
            Bit 7 = Arming Input bit 16 ON,
byte 11     Bit 0 = Arming Input bit 17 ON,
            Bit 1 = Arming Input bit 18 ON,
            Bit 2 = Arming Input bit 19 ON,
            Bit 3 = Arming Input bit 20 ON,
            Bit 4 = Arming Input bit 21 ON,
            Bit 5 = Arming Input bit 22 ON,
            Bit 6 = Arming Input bit 23 ON,
            Bit 7 = Arming Input bit 24 ON,
byte 12     Bit 0 = Arming Input bit 25 ON,
            Bit 1 = Arming Input bit 26 ON,
            Bit 2 = Arming Input bit 27 ON,
            Bit 3 = Arming Input bit 28 ON,
            Bit 4 = Arming Input bit 29 ON,
            Bit 5 = Arming Input bit 30 ON,
            Bit 6 = Arming Input bit 31 ON,
            Bit 7 = Arming Input bit 32 ON,
<Parameter Type> Configuration 
<Withdrawn>
<Informative> This object has been withdrawn as it was determined that TSS
should provide raw readings without delays applied. Further, this object used
confusing bit ordering. See D.3.1 for more details.
<Object Identifier> 1.3.6.1.4.1.1206.4.2.4.1.12.1.5"
::= { outputConditioningEntry 5 }

-- 5.2.12.6 Zone Output Extend Time
sensorZoneOutputExtendTime  OBJECT-TYPE
SYNTAX  Integer32 (0..65535)
UNITS   "deciseconds"
MAX-ACCESS  read-write
STATUS  current
DESCRIPTION 
"<Definition> The output for the zone is extended, after the end of the period
in which the sensor zone is occupied, by the amount of time specified (tenths
of a second: 00.0 to 6553.5 sec).
<Parameter Type> Configuration 
<Object Identifier> 1.3.6.1.4.1.1206.4.2.4.1.12.1.6"
REFERENCE
"NEMA TS2 Clause 3.5.5.5.4.d and 6.5.2.24.2"  
::= { outputConditioningEntry 6 }

-- 5.2.12.7 Zone Output Extend Mode
sensorZoneOutputExtendMode  OBJECT-TYPE
SYNTAX  INTEGER {
                 extendEnablesHaveNoEffect (1),
                 extendEnablesORedActive (2),
                 extendEnablesORedNotActive (3),
                 extendEnablesANDedActive (4),
                 extendEnablesANDedNotActive (5) }
MAX-ACCESS  read-write
STATUS  current
DESCRIPTION
"<Definition> This parameter determines if and how the extend enables will be
used to modify the operation of the extend feature. 
      extendEnablesHaveNoEffect(1) - The extend enables have no effect on the
      extend feature of the zone.
      extendEnablesORedActive(2) - If any of the extend enables are active 
      the extend feature is active, else the extend feature is not active.
      extendEnablesORedNotActive(3) - If any of the extend enables are active
      the extend feature is not active, else the extend feature is active.
      extendEnablesANDedActive(4) - If all the extend enables are active the
      extend feature is active, else the extend feature is not active.
      extendEnablesANDedNotActive(5) - If all of the extend enables are 
      active the extend feature is not active, else the extend feature is
      active.
<Parameter Type> Configuration 
<Object Identifier> 1.3.6.1.4.1.1206.4.2.4.1.12.1.7"
::= { outputConditioningEntry 7 }

-- 5.2.12.8 Zone Output Extend Enables
sensorZoneOutputExtendEnables  OBJECT-TYPE
SYNTAX     TssBitmap96
MAX-ACCESS read-write
STATUS     deprecated
DESCRIPTION
"<Definition> This bit-mapped parameter identifies which Arming Pins, Arming
Input Bits, and which state for each are to be used as enables for the extend
feature. If the Arming Pin inputs are DC then a low input is an ON and a high
input is an OFF. If the Arming Pin inputs are AC then a low input is an OFF and
a high input is an ON.
<Format>
byte 1      Bit 0 = Arming Pin 1 OFF,
            Bit 1 = Arming Pin 2 OFF,
            Bit 2 = Arming Pin 3 OFF,
            Bit 3 = Arming Pin 4 OFF,
            Bit 4 = Arming Pin 5 OFF,
            Bit 5 = Arming Pin 6 OFF,
            Bit 6 = Arming Pin 7 OFF,
            Bit 7 = Arming Pin 8 OFF,
byte 2      Bit 0 = Arming Pin 9 OFF,
            Bit 1 = Arming Pin 10 OFF,
            Bit 2 = Arming Pin 11 OFF,
            Bit 3 = Arming Pin 12 OFF,
            Bit 4 = Arming Pin 13 OFF,
            Bit 5 = Arming Pin 14 OFF,
            Bit 6 = Arming Pin 15 OFF,
            Bit 7 = Arming Pin 16 OFF,
byte 3      Bit 0 = Arming Pin 1 ON,
            Bit 1 = Arming Pin 2 ON,
            Bit 2 = Arming Pin 3 ON,
            Bit 3 = Arming Pin 4 ON,
            Bit 4 = Arming Pin 5 ON,
            Bit 5 = Arming Pin 6 ON,
            Bit 6 = Arming Pin 7 ON,
            Bit 7 = Arming Pin 8 ON,
Byte 4      Bit 0 = Arming Pin 9 ON,
            Bit 1 = Arming Pin 10 ON,
            Bit 2 = Arming Pin 11 ON,
            Bit 3 = Arming Pin 12 ON,
            Bit 4 = Arming Pin 13 ON,
            Bit 5 = Arming Pin 14 ON,
            Bit 6 = Arming Pin 15 ON,
            Bit 7 = Arming Pin 16 ON,
byte 5      Bit 0 = Arming Input bit 1 OFF,
            Bit 1 = Arming Input bit 2 OFF,
            Bit 2 = Arming Input bit 3 OFF,
            Bit 3 = Arming Input bit 4 OFF,
            Bit 4 = Arming Input bit 5 OFF,
            Bit 5 = Arming Input bit 6 OFF,
            Bit 6 = Arming Input bit 7 OFF,
            Bit 7 = Arming Input bit 8 OFF,
byte 6      Bit 0 = Arming Input bit 9 OFF,
            Bit 1 = Arming Input bit 10 OFF,
            Bit 2 = Arming Input bit 11 OFF,
            Bit 3 = Arming Input bit 12 OFF,
            Bit 4 = Arming Input bit 13 OFF,
            Bit 5 = Arming Input bit 14 OFF,
            Bit 6 = Arming Input bit 15 OFF,
            Bit 7 = Arming Input bit 16 OFF,
byte 7      Bit 0 = Arming Input bit 17 OFF,
            Bit 1 = Arming Input bit 18 OFF,
            Bit 2 = Arming Input bit 19 OFF,
            Bit 3 = Arming Input bit 20 OFF,
            Bit 4 = Arming Input bit 21 OFF,
            Bit 5 = Arming Input bit 22 OFF,
            Bit 6 = Arming Input bit 23 OFF,
            Bit 7 = Arming Input bit 24 OFF,
byte 8      Bit 0 = Arming Input bit 25 OFF,
            Bit 1 = Arming Input bit 26 OFF,
            Bit 2 = Arming Input bit 27 OFF,
            Bit 3 = Arming Input bit 28 OFF,
            Bit 4 = Arming Input bit 29 OFF,
            Bit 5 = Arming Input bit 30 OFF,
            Bit 6 = Arming Input bit 31 OFF,
            Bit 7 = Arming Input bit 32 OFF,
byte 9      Bit 0 = Arming Input bit 1 ON,
            Bit 1 = Arming Input bit 2 ON,
            Bit 2 = Arming Input bit 3 ON,
            Bit 3 = Arming Input bit 4 ON,
            Bit 4 = Arming Input bit 5 ON,
            Bit 5 = Arming Input bit 6 ON,
            Bit 6 = Arming Input bit 7 ON,
            Bit 7 = Arming Input bit 8 ON,
byte 10     Bit 0 = Arming Input bit 9 ON,
            Bit 1 = Arming Input bit 10 ON,
            Bit 2 = Arming Input bit 11 ON,
            Bit 3 = Arming Input bit 12 ON,
            Bit 4 = Arming Input bit 13 ON,
            Bit 5 = Arming Input bit 14 ON,
            Bit 6 = Arming Input bit 15 ON,
            Bit 7 = Arming Input bit 16 ON,
byte 11     Bit 0 = Arming Input bit 17 ON,
            Bit 1 = Arming Input bit 18 ON,
            Bit 2 = Arming Input bit 19 ON,
            Bit 3 = Arming Input bit 20 ON,
            Bit 4 = Arming Input bit 21 ON,
            Bit 5 = Arming Input bit 22 ON,
            Bit 6 = Arming Input bit 23 ON,
            Bit 7 = Arming Input bit 24 ON,
byte 12     Bit 0 = Arming Input bit 25 ON,
            Bit 1 = Arming Input bit 26 ON,
            Bit 2 = Arming Input bit 27 ON,
            Bit 3 = Arming Input bit 28 ON,
            Bit 4 = Arming Input bit 29 ON,
            Bit 5 = Arming Input bit 30 ON,
            Bit 6 = Arming Input bit 31 ON,
            Bit 7 = Arming Input bit 32 ON,
<Parameter Type> Configuration 
<Withdrawn>
<Informative> This object has been withdrawn as it was determined that TSS
should provide raw readings without delays applied. Further, this object used
confusing bit ordering. See D.3.1 for more details.
<Object Identifier> 1.3.6.1.4.1.1206.4.2.4.1.12.1.8"
::= { outputConditioningEntry 8 }

-- 5.2.12.9 Zone Output Sequenced
sensorZoneOutputSequenced  OBJECT-TYPE
SYNTAX  Integer32 (0..255)
MAX-ACCESS  read-write
STATUS  current
DESCRIPTION
"<Definition> This parameter identifies the sensorZoneNumber of an upstream
directional zone. The output for this entry shall only become active if the
zone is actuated when the upstream directional zone has an active output. The
output for this entry shall not activate for any actuation (or during the
subsequent occupancy) that occurs when the upstream directional zone does not
have an active output. This entry shall report each new actuation that occurs
while the upstream directional zone output remains active. 
<Parameter Type> Configuration 
<Informative> This parameter allows the creation of directional detection. The
intent is that the two zones are in close enough proximity that a vehicle is
able to be detected by both zones and that the last zone to detect the vehicle
is the one that activates its output.

A report of an actuation may not result in an active output if other
configuration parameters prevent the activation (e.g., an actuation with a
occupancy that is shorter than sensorZoneOutputDelayTime).
<Object Identifier> 1.3.6.1.4.1.1206.4.2.4.1.12.1.9"
::= { outputConditioningEntry 9 }

-- 5.2.13 Pending Configuration File Name
pendingConfigurationFileName  OBJECT-TYPE
SYNTAX  OCTET STRING (SIZE(8..32))
MAX-ACCESS  read-write
STATUS  deprecated
DESCRIPTION
"<Definition> This identifies the name of the pending configuration file that
is used by the TSS upon issuing the executePendingConfiguration command.
<Parameter Type> Configuration 
<Withdrawn>
<Informative> This functionality is expected to be addressed in a future
edition of ISO 26048-1.
<Object Identifier> 1.3.6.1.4.1.1206.4.2.4.1.13"
::= { tssSystemSetup 13}

-- 5.2.14 External Arming Inputs Version 3
externalArmingInputsV3  OBJECT-TYPE
SYNTAX  ITSBitmap (SIZE(8))
MAX-ACCESS  read-write
STATUS  current
DESCRIPTION
"<Definition> This allows other devices to modify the states of the Arming
Input Bits used by the TSS. There are separate clears and sets so that
individual Arming Input Bits can be managed by different management stations.
While the inputs are physically configured within each deployment, it is
envisioned that the first 24 bits will typically correspond to the Greens,
Yellows, and Reds of phases 1 through 8 from the traffic signal controller
leaving the remaining 8 bits for other phases, overlaps, or special functions.
If the Arming Pin inputs are DC then a low input is an ON and a high input is
an OFF. If the Arming Pin inputs are AC then a low input is an OFF and a high
input is an ON.
An attempt to write to this object with a value that has an Arming Input
configured to both Clear and Set (e.g., Bits 0 and 32 are set) shall result in
a 'wrongValue' error. A read of this object shall return the last value
written. 
<Format>
For Bits 0-31 of the ITSBitmap: Bit x = Clear Arming Input Bit x + 1;
For Bits 32-63 of the ITSBitmap: Bit x = Set Arming Input Bit x - 31
<Informative> For example, for the value 0x80 00 00 00 04 00 00 00, 
 - Bit 0 is set indicating that Arming Input Bit 1 is cleared and 
 - Bit 33 is set indicating that Arming Input Bit 2 is set
<Parameter Type> Configuration 
<Informative> For example, two management stations can coordinate so that the
first management station agrees to only use (set or clear) bits associated with
arming inputs 1 and 2 while the other management station agrees to not use the
bits associated with those two arming inputs.
<Object Identifier> 1.3.6.1.4.1.1206.4.2.4.1.14"
::= { tssSystemSetup 14 }

-- 5.2.15 External Arming Bit Status
externalArmingBitStatus  OBJECT-TYPE
SYNTAX     ITSBitmap (SIZE(4))
MAX-ACCESS read-only
STATUS     current
DESCRIPTION
"<Definition> The current state of the Arming Input Bits used by the TSS. 
<Format>
Bit x = Clear Arming Input Bit x + 1
<Informative> For example, for the value 0x80 00 00 00, 
 - Bit 0 is set indicating that Arming Input Bit 1 is ON 
<Parameter Type> Configuration 
<Informative> For example, two management stations can coordinate so that the
first management station agrees to only use (set or clear) bits associated with
arming inputs 1 and 2 while the other management station agrees to not use the
bits associated with those two arming inputs.
<Object Identifier> 1.3.6.1.4.1.1206.4.2.4.1.15"
::= { tssSystemSetup 15 }

-- 5.2.16 Maximum Restart Time
tssRestartTimeMax OBJECT-TYPE
SYNTAX     ITSUnsigned8
UNITS      "seconds"
MAX-ACCESS read-only
STATUS     current
DESCRIPTION
"<Definition> The manufacturer-specified maximum duration after setting
sensorSystemStatus until the TSS is able to respond to SNMP requests. 
<Parameter Type> Status 
<Informative> During the reboot process, functions are interrupted. This value
assists command generators to manage expecations on how long to wait during a
reboot.
<Object Identifier> 1.3.6.1.4.1.1206.4.2.4.1.16"
::= { tssSystemSetup 16 }

-- 5.3 SENSOR CONTROL OBJECTS
tssControl OBJECT-IDENTITY 
STATUS  current
DESCRIPTION
"This node is an identifier used to group all objects for TSS output control
data elements. A sensor zone can be mapped to any available output. Outputs
report discrete activity states sensed within a zone combined with other logic.
Output states should be refreshed upon change of actuation state for each
associated detector or any other parameters associated with the logic.
<Object Identifier> 1.3.6.1.4.1.1206.4.2.4.2"
::= { tss 2 }

-- 5.3.1 Maximum Number of Outputs
maxOutputNumber  OBJECT-TYPE
SYNTAX  Integer32 (1..255)
UNITS   "outputs"
MAX-ACCESS  read-only
STATUS  current
DESCRIPTION
"<Definition> Indicates the maximum number of outputs supported by this TSS.
<Parameter Type> Status 
<Object Identifier> 1.3.6.1.4.1.1206.4.2.4.2.1"
::= { tssControl 1 }

-- 5.3.2 Output Configuration Table
outputConfigurationTable  OBJECT-TYPE
SYNTAX  SEQUENCE OF OutputConfigurationEntry
MAX-ACCESS  not-accessible
STATUS  current
DESCRIPTION 
"<Description> Table containing configuration data elements for each TSS
physical output. The number of rows in this table is equal to the
maxOutputNumber data element. Table rows are set by the manufacturer, and row
creation/deletion is not supported.
<TableType> static
<Object Identifier> 1.3.6.1.4.1.1206.4.2.4.2.2"
::= { tssControl 2 }  

outputConfigurationEntry  OBJECT-TYPE
SYNTAX  OutputConfigurationEntry
MAX-ACCESS  not-accessible
STATUS  current
DESCRIPTION 
"<Definition> Row containing output configuration data elements.
<Object Identifier> 1.3.6.1.4.1.1206.4.2.4.2.2.1"
INDEX { outputNumber }
::= { outputConfigurationTable 1}

OutputConfigurationEntry ::= SEQUENCE {
      outputNumber                  Integer32,
      outputSensorZoneNumber        Integer32,
      outputFailsafeMode            INTEGER,
      outputModeStatus              NtcipOctetBitmap8,
      outputLabel                   SnmpAdminString,
      outputArmingEnables           TssBitmap96,
      outputArmingMode              INTEGER,
      outputFailsafeModeV3          INTEGER,
      outputFailsafeReset           TruthValue,
      outputOverrideMode            INTEGER,
      outputModeStatusV3            BITS,
      outputArmingEnablesV3         BITS }

-- 5.3.2.1 Output Number
outputNumber  OBJECT-TYPE
SYNTAX  Integer32 (1..255)
MAX-ACCESS  read-only
STATUS  current
DESCRIPTION 
"<Definition> The numerical label or number assigned to a physical output. This
is also the index value that uniquely identifies this entry.
<Parameter Type> Status 
<Object Identifier> 1.3.6.1.4.1.1206.4.2.4.2.2.1.1"
::= { outputConfigurationEntry 1 }

-- 5.3.2.2 Output Sensor Zone Number
outputSensorZoneNumber  OBJECT-TYPE
SYNTAX  Integer32 (0..255)
MAX-ACCESS  read-write
STATUS  current
DESCRIPTION 
"<Definition>The sensorZoneNumber for the zone associated with this output. A
value of zero (0) indicates that no zone is associated with this output. When
read, this data element returns the last value written.
<Parameter Type> Configuration 
<Object Identifier> 1.3.6.1.4.1.1206.4.2.4.2.2.1.2"
::= { outputConfigurationEntry 2}

-- 5.3.2.3 Output Failsafe Mode
outputFailsafeMode  OBJECT-TYPE
SYNTAX  INTEGER {
                 failsafeModeOn (1),
                 failsafeModeOff (2),
                 overrideCommandOn (3),
                 overrideCommandOff (4),
                 normal (5) }
MAX-ACCESS  read-write
STATUS  deprecated
DESCRIPTION 
"<Definition> Data element that allows configuration of outputs for failure
override modes, as follows:
      failsafeModeOn(1) - The output is set to the ON state whenever there is 
      a failure that affects the proper performance of this output;
      failsafeModeOff(2) - The output is set to the OFF state whenever there
      is a failure that affects the proper performance of this output;
      overrideCommandOn(3) - The output is set to the ON state, overriding 
      the normal operational state of the output;
      overrideCommandOff(4) - The output is set to the OFF state, overriding
      the normal operational state of the output;
      normal(5) - The output is returned to its normal operational state.
      When read, this data element returns the last value written except for
      the value of 5. After a value of 5 is written, the value prior to the
      normal command is returned.
<Parameter Type> Configuration 
<Superseded by> outputFailsafeModeV3, outputFailsafeReset, outputOverrideMode
<Informative> This object was deprecated in v03 to resolve ambiguities.
<Object Identifier> 1.3.6.1.4.1.1206.4.2.4.2.2.1.3"
::= { outputConfigurationEntry 3 } 

-- 5.3.2.4 Output Mode Status
outputModeStatus  OBJECT-TYPE
SYNTAX  NtcipOctetBitmap8
MAX-ACCESS  read-only
STATUS  deprecated
DESCRIPTION 
"<Definition> A bit-mapped value as defined below for reading the status of
failure override modes, as follows:
<Format>
1 - detected failure. On. On. -   -
2 - failsafe mode.    On. Off -   -
3 - override          Off Off on. Off
3 - output            on. Off on  off
bit 7       0 = OFF, 1 = ON         For Failsafe Mode Status ON indicates the
                                    Failsafe Mode is ON, meaning that the
                                    output assumes an ON state whenever there
                                    is a failure that in any way affects the
                                    proper performance of this outputand
                                    Failsafe Mode Status OFF indicates the
                                    status of the Failsafe Mode is OFF,
                                    meaning that the output assumes an OFF
                                    state whenever there is a failure that in
                                    any way affects the proper performance of
                                    this output (MSB);
bit 6       0 = OFF, 1 = ON         For Override Command Status ON indicates
                                    the presence of an Override to the normal
                                    operational state of the output to ON and
                                    Override Command Status Off indicates the
                                    presence of an Override to the normal
                                    operational state of the output to OFF;
bit 5..0                            Reserved (bit 0 = LSB).
<Parameter Type> Status 
<Superseded by> outputModeStatusV3
<Informative> This object was deprecated in v03 to resolve ambiguities.
<Object Identifier> 1.3.6.1.4.1.1206.4.2.4.2.2.1.4"
::= { outputConfigurationEntry 4 } 

-- 5.3.2.5 Output Label
outputLabel  OBJECT-TYPE
SYNTAX  SnmpAdminString (SIZE (8..255))
MAX-ACCESS  read-write
STATUS  current
DESCRIPTION 
"<Definition> Text string to describe the TSS output. A maximum string length
of less than 255 may be supported.
<Parameter Type> Configuration 
<Object Identifier> 1.3.6.1.4.1.1206.4.2.4.2.2.1.5"
::= { outputConfigurationEntry 5 }

-- 5.3.2.6 Output Arming Enables
outputArmingEnables  OBJECT-TYPE
SYNTAX  TssBitmap96
MAX-ACCESS  read-write
STATUS  deprecated
DESCRIPTION 
"<Definition> Consists of up to 16 physical Arming Pins to the TSS and up to 32
bits of external arming bits which can be controlled through this protocol. The
Arming Pins have historically been connected to the phase greens but can be
used for any purpose. It is envisioned that the phase green information could
be sent through Arming Input Bits using the protocol and eliminate the need for
additional wiring. If the Arming Pin inputs are DC then a low input is an ON
and a high input is an OFF. If the Arming Pin inputs are AC then a low input is
an OFF and a high input is an ON.
<Format>
byte 1      Bit 0 = Arming Pin 1 OFF,
            Bit 1 = Arming Pin 2 OFF,
            Bit 2 = Arming Pin 3 OFF,
            Bit 3 = Arming Pin 4 OFF,
            Bit 4 = Arming Pin 5 OFF,
            Bit 5 = Arming Pin 6 OFF,
            Bit 6 = Arming Pin 7 OFF,
            Bit 7 = Arming Pin 8 OFF,
byte 2      Bit 0 = Arming Pin 9 OFF,
            Bit 1 = Arming Pin 10 OFF,
            Bit 2 = Arming Pin 11 OFF,
            Bit 3 = Arming Pin 12 OFF,
            Bit 4 = Arming Pin 13 OFF,
            Bit 5 = Arming Pin 14 OFF,
            Bit 6 = Arming Pin 15 OFF,
            Bit 7 = Arming Pin 16 OFF,
byte 3      Bit 0 = Arming Pin 1 ON,
            Bit 1 = Arming Pin 2 ON,
            Bit 2 = Arming Pin 3 ON,
            Bit 3 = Arming Pin 4 ON,
            Bit 4 = Arming Pin 5 ON,
            Bit 5 = Arming Pin 6 ON,
            Bit 6 = Arming Pin 7 ON,
            Bit 7 = Arming Pin 8 ON,
byte 4      Bit 0 = Arming Pin 9 ON,
            Bit 1 = Arming Pin 10 ON,
            Bit 2 = Arming Pin 11 ON,
            Bit 3 = Arming Pin 12 ON,
            Bit 4 = Arming Pin 13 ON,
            Bit 5 = Arming Pin 14 ON,
            Bit 6 = Arming Pin 15 ON,
            Bit 7 = Arming Pin 16 ON,
byte 5      Bit 0 = Arming Input bit 1 OFF,
            Bit 1 = Arming Input bit 2 OFF,
            Bit 2 = Arming Input bit 3 OFF,
            Bit 3 = Arming Input bit 4 OFF,
            Bit 4 = Arming Input bit 5 OFF,
            Bit 5 = Arming Input bit 6 OFF,
            Bit 6 = Arming Input bit 7 OFF,
            Bit 7 = Arming Input bit 8 OFF,
byte 6      Bit 0 = Arming Input bit 9 OFF,
            Bit 1 = Arming Input bit 10 OFF,
            Bit 2 = Arming Input bit 11 OFF,
            Bit 3 = Arming Input bit 12 OFF,
            Bit 4 = Arming Input bit 13 OFF,
            Bit 5 = Arming Input bit 14 OFF,
            Bit 6 = Arming Input bit 15 OFF,
            Bit 7 = Arming Input bit 16 OFF,
byte 7      Bit 0 = Arming Input bit 17 OFF,
            Bit 1 = Arming Input bit 18 OFF,
            Bit 2 = Arming Input bit 19 OFF,
            Bit 3 = Arming Input bit 20 OFF,
            Bit 4 = Arming Input bit 21 OFF,
            Bit 5 = Arming Input bit 22 OFF,
            Bit 6 = Arming Input bit 23 OFF,
            Bit 7 = Arming Input bit 24 OFF,
byte 8      Bit 0 = Arming Input bit 25 OFF,
            Bit 1 = Arming Input bit 26 OFF,
            Bit 2 = Arming Input bit 27 OFF,
            Bit 3 = Arming Input bit 28 OFF,
            Bit 4 = Arming Input bit 29 OFF,
            Bit 5 = Arming Input bit 30 OFF,
            Bit 6 = Arming Input bit 31 OFF,
            Bit 7 = Arming Input bit 32 OFF,
byte 9      Bit 0 = Arming Input bit 1 ON,
            Bit 1 = Arming Input bit 2 ON,
            Bit 2 = Arming Input bit 3 ON,
            Bit 3 = Arming Input bit 4 ON,
            Bit 4 = Arming Input bit 5 ON,
            Bit 5 = Arming Input bit 6 ON,
            Bit 6 = Arming Input bit 7 ON,
            Bit 7 = Arming Input bit 8 ON,
byte 10     Bit 0 = Arming Input bit 9 ON,
            Bit 1 = Arming Input bit 10 ON,
            Bit 2 = Arming Input bit 11 ON,
            Bit 3 = Arming Input bit 12 ON,
            Bit 4 = Arming Input bit 13 ON,
            Bit 5 = Arming Input bit 14 ON,
            Bit 6 = Arming Input bit 15 ON,
            Bit 7 = Arming Input bit 16 ON,
byte 11     Bit 0 = Arming Input bit 17 ON,
            Bit 1 = Arming Input bit 18 ON,
            Bit 2 = Arming Input bit 19 ON,
            Bit 3 = Arming Input bit 20 ON,
            Bit 4 = Arming Input bit 21 ON,
            Bit 5 = Arming Input bit 22 ON,
            Bit 6 = Arming Input bit 23 ON,
            Bit 7 = Arming Input bit 24 ON,
byte 12     Bit 0 = Arming Input bit 25 ON,
            Bit 1 = Arming Input bit 26 ON,
            Bit 2 = Arming Input bit 27 ON,
            Bit 3 = Arming Input bit 28 ON,
            Bit 4 = Arming Input bit 29 ON,
            Bit 5 = Arming Input bit 30 ON,
            Bit 6 = Arming Input bit 31 ON,
            Bit 7 = Arming Input bit 32 ON.
<Parameter Type> Configuration 
<Superseded by> outputArmingEnablesV3
<Informative> This object was deprecated in v03 to resolve ambiguities
regarding bit order.
<Object Identifier> 1.3.6.1.4.1.1206.4.2.4.2.2.1.6"
::= { outputConfigurationEntry 6 }

-- 5.3.2.7 Output Arming Mode
outputArmingMode  OBJECT-TYPE
SYNTAX  INTEGER {
                 armingEnablesHaveNoEffect (1),
                 normOffArmingEnablesORedZone (2),
                 normOnArmingEnablesORedZone (3),
                 normZoneArmingEnablesORedOff (4),
                 normZoneArmingEnablesORedOn (5),
                 normOffArmingEnablesANDedZone (6),
                 normOnArmingEnablesANDedZone (7),
                 normZoneArmingEnablesANDedOff (8),
                 normZoneArmingEnablesANDedOn (9)}
MAX-ACCESS  read-write
STATUS  current
DESCRIPTION 
"<Definition> This parameter determines if and how the Arming Enables are used
to modify the operation of this output.
      armingEnablesHaveNoEffect(1) - The Arming Enables have no effect on the
      output of the zone.
      normOffArmingEnablesORedZone(2) - The zone output is OFF when none of
      the Arming Enables are active; the zone output indicates the actual 
      zone state when any of the Arming Enables are active.
      normOnArmingEnablesORedZone(3) - The zone output is ON when none of
      the Arming Enables are active; the zone output indicates the actual 
      zone state when any of the Arming Enables are active.
      normZoneArmingEnablesORedOff(4) - The zone output is the actual zone
      state when none of the Arming Enables are active, and OFF when any of
      the Arming Enables are active.
      normZoneArmingEnablesORedOn(5) - The zone output is the actual zone
      state when none of the Arming Enables are active, and ON when any of
      the Arming Enables are active.
      normOffArmingEnablesANDedZone(6) - The zone output is OFF when any of
      the Arming Enables are not active, and the actual zone state when all
      of the Arming Enables are active.
      normOnArmingEnablesANDedZone(7) - The zone output is ON when any of
      the Arming Enables are not active, and the actual zone state when all
      of the Arming Enables or active.
      normZoneArmingEnablesANDedOff(8) - The zone output is the actual zone
      state when any of the Arming Enables are not active, and OFF when all
      of the Arming Enables are active.
      normZoneArmingEnablesANDedOn(9) - The zone output is the actual zone
      state when any of the Arming Enables are not active, and ON when all of
      the Arming Enables are active.
<Parameter Type> Configuration 
<Informative> The state of the zone output for each of the numbered arming
modes are summarized in the following table. A hyphen indicates that the Arming
Enables have no effect on the output of the zone. 
          +--------+------+---+---+---+---+---+---+---+---+---+
          |  Arming Mode  | 1 | 2 | 3 | 4 | 5 | 6 | 7 | 8 | 9 |
          +--------+------+---+---+---+---+---+---+---+---+---+
          |        | None | - |Off| On| - | - |Off| On| - | - |
          | # of   +------+---+---+---+---+---+---+---+---+---+
          | Arming | Some | - | - | - |Off| On|Off| On| - | - |
          |Enables +------+---+---+---+---+---+---+---+---+---+
          | Active | All  | - | - | - |Off| On| - | - |Off| On|
          |--------+------+---+---+---+---+---+---+---+---+---+
<Object Identifier> 1.3.6.1.4.1.1206.4.2.4.2.2.1.7"
::= { outputConfigurationEntry 7 }

-- 5.3.2.8 Output Failsafe Mode Version 3
outputFailsafeModeV3  OBJECT-TYPE
SYNTAX  INTEGER {
                 failsafeModeOn (1),
                 failsafeModeOff (2) }
MAX-ACCESS  read-write
STATUS  current
DESCRIPTION 
"<Definition> Indicates the state that the output will assume when the TSS
detects a failure that affects the proper performance of this output
<Format> Valid values follow:
      failsafeModeOn(1) - The output is set to the ON state whenever the TSS
      detects a failure;
      failsafeModeOff(2) - The output is set to the OFF state whenever the
      TSS detects a failure; 
<Parameter Type> Configuration 
<Object Identifier> 1.3.6.1.4.1.1206.4.2.4.2.2.1.8"
::= { outputConfigurationEntry 8 } 

-- 5.3.2.9 Output Failsafe Reset
outputFailsafeReset OBJECT-TYPE
SYNTAX     TruthValue
MAX-ACCESS read-write
STATUS     current
DESCRIPTION 
"<Definition> When set to true, the TSS shall reset the failsafe logic. Upon
completion, this object shall transition back to false. The TSS may reset the
failsafe logic on its own without the use of this object. The TSS shall return
the output to the failsafe mode after a reset if it detects a failure.
<Parameter Type> Control 
<Object Identifier> 1.3.6.1.4.1.1206.4.2.4.2.2.1.9"
::= { outputConfigurationEntry 9 } 

-- 5.3.2.10 Output Override Mode
outputOverrideMode  OBJECT-TYPE
SYNTAX  INTEGER {
                 normal (1),
                 overrideCommandOn (2),
                 overrideCommandOff (3) }
MAX-ACCESS  read-write
STATUS  current
DESCRIPTION 
"<Definition> Indicates the current override state for the output. 
<Format> Valid values follow:
      normal(1) - The output is not overridden;
      overrideCommandOn(2) - The output is overridden to the ON state;
      overrideCommandOff(3) - The output is overridden to the OFF state.
<Parameter Type> Configuration 
<Object Identifier> 1.3.6.1.4.1.1206.4.2.4.2.2.1.10"
::= { outputConfigurationEntry 10 } 

-- 5.3.2.11 Output Mode Status Version 3
outputModeStatusV3  OBJECT-TYPE
SYNTAX     BITS { failsafeOn (0),
               failsafeOff (1),
               overrideOn (2),
               overrideOff (3) }
MAX-ACCESS read-only
STATUS     current
DESCRIPTION 
"<Definition> Indicates which, if any, of the indicated conditions are
currently active. 
<Format> When all bits are zero, none of the following conditions are affecting
the state of the output. 
failsafeOn (0): When set, a failure has been detected and failsafeModeOn of 
  outputFailsafeModeV3 is applied changing the output to ON (unless 
  overridden);
failsafeOff (1): When set, a failure has been detected and failsafeModeOff of 
  outputFailsafeModeV3 is applied changing the output to OFF (unless 
  overridden);
overrideOn (2): When set, the output is forced to ON. 
overrideOff (3): When set, the output is forced to OFF. 
<Parameter Type> Status 
<Object Identifier> 1.3.6.1.4.1.1206.4.2.4.2.2.1.11"
::= { outputConfigurationEntry 11 } 

-- 5.3.2.12 Output Arming Enables Version 3
outputArmingEnablesV3  OBJECT-TYPE
SYNTAX  BITS {pin1off(0),     pin2off(1),     pin3off(2),     pin4off(3),
              pin5off(4),     pin6off(5),     pin7off(6),     pin8off(7),
              pin9off(8),     pin10off(9),    pin11off(10),   pin12off(11),
              pin13off(12),   pin14off(13),   pin15off(14),   pin16off(15),
              pin1on(16),     pin2on(17),     pin3on(18),     pin4on(19),
              pin5on(20),     pin6on(21),     pin7on(22),     pin8on(23),
              pin9on(24),     pin10on(25),    pin11on(26),    pin12on(27),
              pin13on(28),    pin14on(29),    pin15on(30),    pin16on(31),
              input1off(32),  input2off(33),  input3off(34),  input4off(35),
              input5off(36),  input6off(37),  input7off(38),  input8off(39),
              input9off(40),  input10off(41), input11off(42), input12off(43),
              input13off(44), input14off(45), input15off(46), input16off(47),
              input17off(48), input18off(49), input19off(50), input20off(51),
              input21off(52), input22off(53), input23off(54), input24off(55),
              input25off(56), input26off(57), input27off(58), input28off(59),
              input29off(60), input30off(61), input31off(62), input32off(63),
              input1on(64),   input2on(65),   input3on(66),   input4on(67),
              input5on(68),   input6on(69),   input7on(70),   input8on(71),
              input9on(72),   input10on(73),  input11on(74),  input12on(75),
              input13on(76),  input14on(77),  input15on(78),  input16on(79),
              input17on(80),  input18on(81),  input19on(82),  input20on(83),
              input21on(84),  input22on(85),  input23on(86),  input24on(87),
              input25on(88),  input26on(89),  input27on(90),  input28on(91),
              input29on(92),  input30on(93),  input31on(94),  input32on(95) }
MAX-ACCESS  read-write
STATUS      current
DESCRIPTION 
"<Definition> Consists of up to 16 physical Arming Pins to the TSS and up to 32
external arming bits which can be controlled through this protocol. The Arming
Pins have historically been connected to the phase greens but can be used for
any purpose. It is envisioned that the phase green information could be sent
through Arming Input Bits using the protocol and eliminate the need for
additional wiring. If the Arming Pin inputs are DC then a low input is an ON
and a high input is an OFF. If the Arming Pin inputs are AC then a low input is
an OFF and a high input is an ON.
<Parameter Type> Configuration 
<Object Identifier> 1.3.6.1.4.1.1206.4.2.4.2.2.1.12"
::= { outputConfigurationEntry 12 }

-- 5.3.3 Maximum Number of Output Groups
maxOutputGroups  OBJECT-TYPE
SYNTAX  Integer32 (1..32)
UNITS   "output groups"
MAX-ACCESS  read-only
STATUS  current
DESCRIPTION 
"<Definition> Indicates the maximum number of output groups supported by this
TSS.
<Parameter Type> Status 
<Object Identifier> 1.3.6.1.4.1.1206.4.2.4.2.3"
::= { tssControl 3 }

-- 5.3.4 Output Group Table
outputGroupTable  OBJECT-TYPE
SYNTAX  SEQUENCE OF OutputGroupEntry
MAX-ACCESS  not-accessible
STATUS  current
DESCRIPTION 
"<Definition> A table containing input and output states for groups of eight
outputs. Each output group represents a multiple of eight (8) sequentially
numbered outputs. Output Group 1 consists of Outputs 1 to 8, Output Group 2
consists of Outputs 9 to 16, etc. The number of rows in this table is equal to
the maxOutputGroups data element. Table rows are set by the manufacturer, and
row creation/deletion is not supported.
<TableType> static
<Object Identifier> 1.3.6.1.4.1.1206.4.2.4.2.4"
::= { tssControl 4 }

outputGroupEntry  OBJECT-TYPE
SYNTAX  OutputGroupEntry
MAX-ACCESS  not-accessible
STATUS  current
DESCRIPTION 
"<Definition> Table for output states, in groups of eight outputs. Each output
group represents a multiple of eight (8) sequentially numbered outputs.
Example: Output Group 1 consists of Outputs 1 to 8, Output Group 2 consists of
Outputs 9 to 16, etc.
<Object Identifier> 1.3.6.1.4.1.1206.4.2.4.2.4.1"

INDEX { outputGroupNumber }
::= { outputGroupTable 1 }

OutputGroupEntry ::= SEQUENCE {
            outputGroupNumber             Integer32,
            outputGroupOutputState        ITSBitmap }

-- 5.3.4.1 Output Group Number
outputGroupNumber  OBJECT-TYPE
SYNTAX  Integer32 (1..32)
UNITS   "outputs"
MAX-ACCESS  read-only
STATUS  current
DESCRIPTION 
"<Definition> Number of the output group, in groups of eight outputs. Each
output group represents a multiple of eight (8) sequentially numbered outputs.
Output Group 1 consists of Outputs 1 to 8, Output Group 2 consists of Outputs 9
to 16, etc.
<Parameter Type> Status 
<Object Identifier> 1.3.6.1.4.1.1206.4.2.4.2.4.1.1"
::= { outputGroupEntry 1 }

-- 5.3.4.2 Output Group Output State
outputGroupOutputState  OBJECT-TYPE
SYNTAX  ITSBitmap (SIZE (1))
MAX-ACCESS  read-only
STATUS  current
DESCRIPTION 
"<Definition> Each bit represents the output state for each output within the
output group. Each output group represents a multiple of eight (8) sequentially
numbered outputs as shown below. Example: Output Group 1 consists of Outputs 1
to 8, Output Group 2 consists of Outputs 9 to 16, etc. 
<Format>
      Bit 0   For output (outputGroupNumber - 1) * 8 + 8,
      Bit 1   For output (outputGroupNumber - 1) * 8 + 7,
      Bit 2   For output (outputGroupNumber - 1) * 8 + 6,
      Bit 3   For output (outputGroupNumber - 1) * 8 + 5,
      Bit 4   For output (outputGroupNumber - 1) * 8 + 4,
      Bit 5   For output (outputGroupNumber - 1) * 8 + 3,
      Bit 6   For output (outputGroupNumber - 1) * 8 + 2,
      Bit 7   For output (outputGroupNumber - 1) * 8 + 1.
<Parameter Type> Status 
<Informative> Per ITSBitmap, Bit 0 is the high-order bit.
<Object Identifier> 1.3.6.1.4.1.1206.4.2.4.2.4.1.2"
::= { outputGroupEntry 2 }

-- 5.4 TSS DATA COLLECTION OBJECTS
tssDataCollection OBJECT-IDENTITY 
STATUS  current
DESCRIPTION
"This node is for data collection elements.
<Object Identifier> 1.3.6.1.4.1.1206.4.2.4.3"
::= { tss 3 }

-- 5.4.1 Data Collection Table
dataCollectionTable OBJECT-TYPE
SYNTAX  SEQUENCE OF DataCollectionEntry
MAX-ACCESS  not-accessible
STATUS  deprecated
DESCRIPTION 
"<Definition> Table containing the most recently completed sample period data.
The number of rows in this table is equal to the maxSensorZones data element.
Table rows are set by the manufacturer, and row creation/deletion is not
supported.
If this object is supported, it reports the same data that is returned using
the new object sampleDataTable with a sampleZoneClass of one and a
sampleEntryNum of two.
<Superseded by> zoneSequenceTable and the sampleDataTable, entry number 2
<Informative> This object was deprecated in NTCIP 1209 v02.
<TableType> static
<Object Identifier> 1.3.6.1.4.1.1206.4.2.4.3.1"
::= { tssDataCollection 1 }

dataCollectionEntry OBJECT-TYPE
SYNTAX  DataCollectionEntry
MAX-ACCESS  not-accessible
STATUS  deprecated
DESCRIPTION 
"<Definition> Table for data collection parameters. 
<Superseded by> zoneSequenceEntry and the sampleDataEntry, entry number 2
<Informative> This object was deprecated in NTCIP 1209 v02.
<Object Identifier> 1.3.6.1.4.1.1206.4.2.4.3.1.1"

INDEX { sensorZoneNumber }
::= { dataCollectionTable 1 }

DataCollectionEntry ::= SEQUENCE {
      endTime           Unsigned32,
      volumeData        Integer32,
      percentOccupancy  Integer32,
      speedData         Integer32,
      zoneStatus        INTEGER }

-- 5.4.1.1 End Time
endTime  OBJECT-TYPE
SYNTAX     Unsigned32
UNITS      "seconds"
MAX-ACCESS read-only
STATUS     deprecated
DESCRIPTION 
"<Definition> Indicates the time at which the data collection period ended for
the data contained in this row, the most recently completed sample period. If
the clockAvailable data element indicates the presence of a clock, this time
shall be expressed in local time as expressed in the controllerLocalTime data
element (see NTCIP 1201 v03); otherwise, this time shall be expressed in the
number of seconds since the most recent TSS initialization.
<Parameter Type> Status 
<Superseded by> sampleEndTime.x.2.1, where x = the sensorZoneNumber of this
entry. If this object is supported, it must report the same value as the
superceding object.
<Informative> This object was deprecated in NTCIP 1209 v02. In SNMPv1, this
object was represented as a Counter; however, the object does not satisfy the
requirements of a Counter and is therefore presented as a Unsigned32 within
SNMPv3. 
<Object Identifier> 1.3.6.1.4.1.1206.4.2.4.3.1.1.1"
::= { dataCollectionEntry 1 }

-- 5.4.1.2 Volume Data
volumeData  OBJECT-TYPE
SYNTAX  Integer32 (0..65535)
UNITS   "counts"
MAX-ACCESS  read-only
STATUS  deprecated
DESCRIPTION
"<Definition> Counts per sample period, for the most recently completed sample
period. Counts are expressed as an integer value in the volumeData data
element. The value of 65535 shall be returned to represent a missing value. A
missing value is reported when the zoneStatus is anything other than OK for the
entire sampling period.
<Parameter Type> Status 
<Superseded by> sampleVolumeData.x.2.1, where x = the sensorZoneNumber of this
entry. If this object is supported, it must report the same value as the
superceding object.
<Informative> This object was deprecated in NTCIP 1209 v02.
<Object Identifier> 1.3.6.1.4.1.1206.4.2.4.3.1.1.2"
::= { dataCollectionEntry 2 }

-- 5.4.1.3 Percent Occupancy
percentOccupancy  OBJECT-TYPE
SYNTAX  Integer32 (0..1000 | 65535)
UNITS   "decipercent"
MAX-ACCESS  read-only
STATUS  deprecated
DESCRIPTION
"<Definition> Percent occupancy over the sample period for the most recently
completed sample period. Occupancy is expressed in tenths of a percent, from 0
to 100.0 percent, in the percentOccupancy data element. The value of 65535
shall be returned to represent an invalid or missing value. A missing value is
reported when the zoneStatus is anything other than OK for the entire sampling
period. Values 1001 through 65534 are reserved for future use.
<Parameter Type> Status 
<Superseded by> samplePercentOccupancy.x.2.1, where x = the sensorZoneNumber of
this entry. If this object is supported, it must report the same value as the
superceding object.
<Informative> This object was deprecated in NTCIP 1209 v02.
<Object Identifier> 1.3.6.1.4.1.1206.4.2.4.3.1.1.3"
::= { dataCollectionEntry 3 }

-- 5.4.1.4 Speed Data
speedData  OBJECT-TYPE
SYNTAX  Integer32 (0..2550 | 65535)
UNITS   "tenths of km/h"
MAX-ACCESS  read-only
STATUS  deprecated
DESCRIPTION
"<Definition> Arithmetic mean of speeds collected over the sample period with
units of 1/10ths of km/h, for the most recently completed sample period. For a
volume of zero during the sample period, the value of 65535 shall be returned
to represent an invalid or missing value. A missing value is reported when the
zoneStatus returned indicates no other status values apply for the entire
sampling period. Values 2551 through 65534 are reserved for future use.
<Parameter Type> Status 
<Superseded by> sampleSpeedData.x.2.1, where x = the sensorZoneNumber of this
entry. If this object is supported, it must report the same value as the
superceding object.
<Informative> This object was deprecated in NTCIP 1209 v02.
<Object Identifier> 1.3.6.1.4.1.1206.4.2.4.3.1.1.4"
-- conversion to English units must be done within the application
::= { dataCollectionEntry 4 }

-- 5.4.1.5 Zone Status
zoneStatus  OBJECT-TYPE
SYNTAX  INTEGER {
                 other (1),
                 oK (2),
                 initializing (3),
                 noActivity (4),
                 maxPresence (5),
                 configurationError (6),
                 erraticCounts (7),
                 disabled (8),
                 overrideActive (9),
                 sensorFailure (10) }
MAX-ACCESS  read-only
STATUS  deprecated
DESCRIPTION 
"<Definition> Detailed status returned as result of diagnostics, as follows:
      Value           Meaning
      Other - Indicates an error has occurred within the TSS for which
      there is no defined definition within this data element,
      oK - Indicates no other status values apply,
      initializing - Indicates an initialization or diagnostics procedure is
      in-progress,
      noActivity - Indicates no activity condition,
      maxPresence - Indicates max presence condition,
      configurationError - Indicates an error within the TSS configuration
      setup,
      erraticCounts - Indicates erratic counts,
      disabled - Indicates that the zone is disabled.
      overrideActive - Indicates an override is active.
      sensorFailure - Indicates a sensing element failure.

If a condition occurs during the sample period, then that state remains for the
duration of that sample period. If multiple conditions occur during a sample
period, the last reported condition, other than OK, is retained.
<Parameter Type> Status 
<Superseded by> sampleVolumeData.x.2.1, where x = the sensorZoneNumber of this
entry. If this object is supported, it must report the same value as the
superceding object.
<Informative> This object was deprecated in NTCIP 1209 v02.
<Object Identifier> 1.3.6.1.4.1.1206.4.2.4.3.1.1.5"
::= { dataCollectionEntry 5 }

-- 5.4.2 Data Buffer Table
dataBufferTable  OBJECT-TYPE
SYNTAX  SEQUENCE OF DataBufferEntry
MAX-ACCESS  not-accessible
STATUS  deprecated
DESCRIPTION 
"<Definition> Table containing the second most recently completed previous
sample period data, which value is specified by the value of the
sensorZoneSamplePeriod data element. The previous period data overwrites the
data for the sample period data immediately preceding the previous sample
period. The number of rows in this table is equal to the maxSensorZones data
element. Table rows are set by the manufacturer, and row creation/deletion is
not supported.
<Superseded by> sampleDataTable for sampleZoneClass of one and a sampleEntryNum
of three. If this table is supported, it must report the same data as the
superceding table.
<Informative> This object was deprecated in NTCIP 1209 v02.
<TableType> static
<Object Identifier> 1.3.6.1.4.1.1206.4.2.4.3.2"
::= { tssDataCollection 2 }

dataBufferEntry  OBJECT-TYPE
SYNTAX  DataBufferEntry
MAX-ACCESS  not-accessible
STATUS  deprecated
DESCRIPTION 
"<Definition> Table containing the data collection parameters for the second
most recently completed previous sample period. 
<Superseded by> sampleDataEntry for sampleZoneClass of one and a sampleEntryNum
of three. If this entry is supported, it must report the same data as the
superceding entry.
<Informative> This object was deprecated in NTCIP 1209 v02.
<Object Identifier> 1.3.6.1.4.1.1206.4.2.4.3.2.1"

INDEX { sensorZoneNumber }
::= { dataBufferTable 1 }

DataBufferEntry ::= SEQUENCE {
      endTimeBuffer           Unsigned32,
      volumeDataBuffer        Integer32,
      percentOccupancyBuffer  Integer32,
      speedDataBuffer         Integer32,
      zoneStatusBuffer        INTEGER }

-- 5.4.2.1 End Time Buffer
endTimeBuffer OBJECT-TYPE
SYNTAX  Unsigned32
UNITS   "seconds"
MAX-ACCESS  read-only
STATUS  deprecated
DESCRIPTION 
"<Definition> Indicates the time at which the data collection period ended for
the data contained in this row, the second most recently completed previous
sample period. If the clockAvailable data element indicates the presence of a
clock, this time shall be expressed in local time as expressed in the
controllerLocalTime data element (see NTCIP 1201 v03); otherwise, this time
shall be expressed in the number of seconds since the most recent TSS
initialization.
<Parameter Type> Status 
<Superseded by> sampleEndTime.x.3.1, where x = the sensorZoneNumber of this
entry. If this object is supported, it must report the same value as the
superceding object.
<Informative> This object was deprecated in NTCIP 1209 v02.
Identifier> 1.3.6.1.4.1.1206.4.2.4.3.2.1.1"
::= { dataBufferEntry 1 }

-- 5.4.2.2 Volume Data Buffer
volumeDataBuffer OBJECT-TYPE
SYNTAX  Integer32 (0..65535)
UNITS   "counts"
MAX-ACCESS  read-only
STATUS  deprecated
DESCRIPTION 
"<Definition> Counts per sample period, for the second most recently completed
previous sample period. Counts are expressed as an integer value in the
volumeData data element. The value of 65535 shall be returned to represent a
missing value. A missing value is reported when the zoneStatusBuffer returned
indicates no other status values apply for the entire sampling period.
<Parameter Type> Status 
<Superseded by> sampleVolumeData.x.3.1, where x = the sensorZoneNumber of this
entry. If this object is supported, it must report the same value as the
superceding object.
<Informative> This object was deprecated in NTCIP 1209 v02.
<Object Identifier> 1.3.6.1.4.1.1206.4.2.4.3.2.1.2"
::= { dataBufferEntry 2 }

-- 5.4.2.3 Percent Occupancy Buffer
percentOccupancyBuffer OBJECT-TYPE
SYNTAX  Integer32 (0..1000 | 65535)
UNITS   "decipercent"
MAX-ACCESS  read-only
STATUS  deprecated
DESCRIPTION 
"<Definition> Percent occupancy over the sample period for the second most
recently completed previous sample period. Occupancy is expressed in tenths of
a percent, from 0 to 100.0 percent, in the percentOccupancy data element. The
value of 65535 shall be returned to represent an invalid or missing value. A
missing value is reported when the zoneStatusBuffer is anything other than OK
for the entire sampling period. Values 1001 through 65534 are reserved for
future use.
<Parameter Type> Status 
<Superseded by> samplePercentOccupancy.x.3.1, where x = the sensorZoneNumber of
this entry. If this object is supported, it must report the same value as the
superceding object.
<Informative> This object was deprecated in NTCIP 1209 v02.
<Object Identifier> 1.3.6.1.4.1.1206.4.2.4.3.2.1.3"
::= { dataBufferEntry 3 }

-- 5.4.2.4 Speed Data Buffer
speedDataBuffer OBJECT-TYPE
SYNTAX  Integer32 (0..2550 | 65535)
UNITS   "tenths of km/h"
MAX-ACCESS  read-only
STATUS  deprecated
DESCRIPTION 
"<Description> Arithmetic mean of speeds collected over the sample period, with
units of 1/10ths of km/hr, for the second most recently completed previous
sample period. For a volume of zero during the sample period, the value of
65535 shall be returned to represent an invalid or missing value. A missing
value is reported when the zoneStatusBuffer is anything other than OK for the
entire sampling period. Values 2551 through 65534 are reserved for future use.
<Parameter Type> Status 
<Superseded by> sampleSpeedData.x.3.1, where x = the sensorZoneNumber of this
entry. If this object is supported, it must report the same value as the
superceding object.
<Informative> This object was deprecated in NTCIP 1209 v02.
<Object Identifier> 1.3.6.1.4.1.1206.4.2.4.3.2.1.4"
::= { dataBufferEntry 4 }

-- 5.4.2.5 Zone Status Buffer
zoneStatusBuffer  OBJECT-TYPE
SYNTAX  INTEGER {
                 other (1),
                 oK (2),
                 initializing (3),
                 noActivity (4),
                 maxPresence (5),
                 configurationError (6),
                 erraticCounts (7),
                 disabled (8),
                 overrideActive (9),
                 sensorFailure (10)
                 }
MAX-ACCESS  read-only
STATUS  deprecated
DESCRIPTION "Detailed status returned as result of diagnostics, for the
previous sample period, as follows:
      Value        Meaning
      Other - Indicates an error has occurred within the TSS for which
      there is no defined definition within this data element,
      oK - Indicates no other status values apply,
      initializing - Indicates an initialization or diagnostics procedure is
      in-progress,
      noActivity - Indicates no activity condition,
      maxPresence - Indicates max presence condition,
      configurationError - Indicates an error within the TSS configuration
      setup,
      erraticCounts - Indicates erratic counts,
      disabled - Indicates that the zone is disabled,
      overrideActive - Indicates an override is active,
      sensorFailure - Indicates a sensing element failure.

If a condition occurs during the sample period, then that state remains for the
duration of that sample period. If multiple conditions occur during a sample
period, the last reported condition, other than OK, is retained.
<Parameter Type> Status 
<Superseded by> sampleZoneStatus.x.3.1, where x = the sensorZoneNumber of this
entry. If this object is supported, it must report the same value as the
superceding object.
<Informative> This object was deprecated in NTCIP 1209 v02.
<Object Identifier> 1.3.6.1.4.1.1206.4.2.4.3.2.1.5"
::= { dataBufferEntry 5 }

-- 5.4.3 Zone Sequence Table
zoneSequenceTable OBJECT-TYPE
SYNTAX  SEQUENCE OF ZoneSequenceTableEntry
MAX-ACCESS  not-accessible
STATUS  current
DESCRIPTION 
"<Definition> Table indicating the number of historical data entries and the
number of classes available for each zone. The maxSensorZones defines the
number of entries in this table. For each zone, retrieve the
numSampleDataEntries available and the sensorZoneClass for those historical
data entries, then retrieve the appropriate data samples from the
sampleDataTable.
<TableType> static
<Object Identifier> 1.3.6.1.4.1.1206.4.2.4.3.3"
::= { tssDataCollection 3 }

zoneSequenceTableEntry OBJECT-TYPE
SYNTAX  ZoneSequenceTableEntry
MAX-ACCESS  not-accessible
STATUS  current
DESCRIPTION 
"<Definition> Entry containing the number of historical data entries and the
number of classes for the indicated zone. The maxSensorZones table defines the
number of entries in this table. 
<Object Identifier> 1.3.6.1.4.1.1206.4.2.4.3.3.1"
INDEX { sensorZoneNumber }
::= { zoneSequenceTable 1 }

ZoneSequenceTableEntry::= SEQUENCE {
      numSampleDataEntries    Integer32,
      numSensorZoneClass      Integer32 }

-- 5.4.3.1 Number of Sample Data Entries
numSampleDataEntries  OBJECT-TYPE
SYNTAX  Integer32 (0..5)
UNITS   "entries"
MAX-ACCESS  read-only
STATUS  current
DESCRIPTION 
"<Definition> The number of valid or partial historical data entries in the
sampleDataTable for the indicated zone. 
<Parameter Type> Status 
<Informative> The sampleDataTable is a static table that contains a constant
number of rows; however, at initialization none of these entries will contain
valid data. This object provides guidance as to which historical data entries
are valid for the indicated zone. Row 1 is always a partial record indicating
data currently being collected (or prematurely being disabled).
Each historical data entry consists of numSensorZoneClass rows.
<Object Identifier> 1.3.6.1.4.1.1206.4.2.4.3.3.1.1"
::= { zoneSequenceTableEntry 1 }

-- 5.4.3.2 Number of Sensor Zone Class
numSensorZoneClass OBJECT-TYPE
SYNTAX  Integer32 (1..255)
UNITS   "classes"
MAX-ACCESS  read-only
STATUS  current
DESCRIPTION 
"<Definition> This is the number of classes currently valid for each valid
historical data entry in the sampleDataTable for the indicated zone.
<Parameter Type> Status 
<Informative> The sampleDataTable is a static table that contains a constant
number of rows; however, not all rows will always contain valid data. This
object provides guidance as to which rows are valid.
Each historical data entry consists of numSensorZoneClass rows.
<Object Identifier> 1.3.6.1.4.1.1206.4.2.4.3.3.1.2"
::= { zoneSequenceTableEntry 2 }

-- 5.4.4 Sample Data Table
sampleDataTable OBJECT-TYPE
SYNTAX  SEQUENCE OF SampleDataEntry
MAX-ACCESS  not-accessible
STATUS  current
DESCRIPTION 
"<Definition> Table containing the historical sample period data. The number of
rows in this table is equal to the maxSensorZones data element multiplied by
the maxSampleDataEntries data element multiplied by the maximum number of
claseses that can be specified (i.e., the maximum value of
numSensorZoneClasses). Table rows are set by the manufacturer, and row
creation/deletion is not supported; however, only the rows indicated by the
zoneSequenceTable will contain valid data.

When a new historical data entry begins for a zone, the value of sampleEntryNum
increments for each row associated with that zone; if the new value of
sampleEntryNum exceeds maxSampleDataEntries, the row is discarded. To
retrieve all historical data entries for a zone, the oldest valid historical
data entry (i.e., as identified by a sampleEntryNum being equal to
numSampleDataEntries for the zone) should be retrieved first (i.e., before it
is discarded). Earlier entries can then be retrieved in order.

A historical data entry consists of all rows with the same pair of values for
sensorZoneNumber and sampleSequenceNumber; however, rows are retrieved by
sensorZoneNumber and sampleEntryNum. Because a new sample period can shift rows
within the table, the management station should verify that the
sampleSequenceNumber is as is expected and to adjust its requests if not. 
<Informative> A sequence number is used rather than end time because the system
clock can be reset between data samples. 
<TableType> static
<Object Identifier> 1.3.6.1.4.1.1206.4.2.4.3.4"
::= { tssDataCollection 4 }

sampleDataEntry OBJECT-TYPE
SYNTAX  SampleDataEntry
MAX-ACCESS  not-accessible
STATUS  current
DESCRIPTION 
"<Definition> Table for data collection parameters. 
<Object Identifier> 1.3.6.1.4.1.1206.4.2.4.3.4.1"

INDEX { sensorZoneNumber, sampleEntryNum, sampleZoneClass }
::= { sampleDataTable 1 }

SampleDataEntry ::= SEQUENCE {
      sampleEntryNum          Integer32,
      sampleZoneClass         Integer32,
      sampleEndTime           Unsigned32,
      sampleVolumeData        Integer32,
      samplePercentOccupancy  Integer32,
      sampleSpeedData         Integer32,
      sampleZoneStatus        INTEGER,
      sampleSequenceNumber    Integer32,
      sampleEndTimeStamp      ITSTimeStamp }

-- 5.4.4.1 Sample Entry Number
sampleEntryNum  OBJECT-TYPE
SYNTAX  Integer32 (1..5)
MAX-ACCESS  read-only
STATUS  current
DESCRIPTION
"<Definition> This identifies which historical sampling period that data is
being requested from. 1 being the sampling period currently in-progress. 2
being the most recently completed sampling period.
<Parameter Type> Status 
<Object Identifier> 1.3.6.1.4.1.1206.4.2.4.3.4.1.1"
::= { sampleDataEntry 1 }

-- 5.4.4.2 Sample Zone Class
sampleZoneClass  OBJECT-TYPE
SYNTAX  Integer32 (1..255)
MAX-ACCESS  read-only
STATUS  current
DESCRIPTION
"<Definition> This identifies the subdivision of collected data (i.e., 'class')
from the sensor zone from which historical sampling period data is being
requested. Class 1 shall always represent all data collected from the zone. If
there are any other classes defined, it will represent the aggregation of the
data from all other classes within the same historical data entry for the zone. 
<Informative> An implementation that reports exactly two classes would be
redundant based on this definition. In other words, if there are only two
classes, Class 1 would aggreate all other classes, but since there is only one
other class (Class 2), it would duplicate its values. 
<Parameter Type> Status 
<Object Identifier> 1.3.6.1.4.1.1206.4.2.4.3.4.1.2"
::= { sampleDataEntry 2 }

-- 5.4.4.3 Sample End Time
sampleEndTime OBJECT-TYPE
SYNTAX  Unsigned32
UNITS   "seconds"
MAX-ACCESS  read-only
STATUS  deprecated
DESCRIPTION 
"<Definition> Indicates the time at which the data collection period ended for
the data contained in this row. If the clockAvailable data element indicates
the presence of a clock, this time shall be expressed in local time as
expressed in the controllerLocalTime data element (see NTCIP 1201 v03);
otherwise, this time shall be expressed in the number of seconds since the most
recent TSS initialization.
<Parameter Type> Status 
<Superseded by> sampleEndTimeStamp
<Informative> This object was deprecated in NTCIP 1209 v03 as it relied on an
old definition of time. Prior to v03, this object was defined as a Counter;
however, the semantics of this object do not align with the definition of a
counter and therefore within SNMPv3, this object is represented as an
Unsigned32.
<Object Identifier> 1.3.6.1.4.1.1206.4.2.4.3.4.1.3"
::= { sampleDataEntry 3 }

-- 5.4.4.4 Sample Volume Data
sampleVolumeData  OBJECT-TYPE
SYNTAX  Integer32 (0..65535)
UNITS   "activations"
MAX-ACCESS  read-only
STATUS  current
DESCRIPTION 
"<Definition> Activations per sample period. Activations are expressed as an
integer value in the sampleVolumeData data element. For a virtual zone (one
created using any AND Boolean functions), volume is the number of times that
the output for the zone was activated. For a virtual zone (one created using
only OR Boolean functions), volume is the additive total of the volumes of all
of the zones that make up the virtual zone. The value of 65534 shall mean 65534
activations or more. The value of 65535 shall be returned to represent a
missing value. A missing value is reported when the zoneStatus is anything
other than OK for the entire sampling period.
<Parameter Type> Status 
<Object Identifier> 1.3.6.1.4.1.1206.4.2.4.3.4.1.4"
::= { sampleDataEntry 4 }

-- 5.4.4.5 Sample Percent Occupancy
samplePercentOccupancy  OBJECT-TYPE
SYNTAX  Integer32 (0..1000 | 65535)
UNITS   "decipercent"
MAX-ACCESS  read-only
STATUS  current
DESCRIPTION 
"<Definition> Percent occupancy over the sample period. Occupancy is expressed
in tenths of a percent, from 0 to 100.0 percent, in the samplePercentOccupancy
data element. For a virtual zone (one created using AND and/or OR Boolean
functions), the percent of time that the output for the zone was activated
shall be returned. The value of 65535 shall be returned to represent an invalid
or missing value. A missing value is reported when the zoneStatus is anything
other than OK for the entire sampling period. Values 1001 through 65534 are
reserved for future use.
<Parameter Type> Status 
<Object Identifier> 1.3.6.1.4.1.1206.4.2.4.3.4.1.5"
::= { sampleDataEntry 5 }

-- 5.4.4.6 Sample Speed Data
sampleSpeedData  OBJECT-TYPE
SYNTAX  Integer32 (0..2550 | 65535)
UNITS   "tenths of km/h"
MAX-ACCESS  read-only
STATUS  current
DESCRIPTION 
"<Definition> Arithmetic mean of speeds collected over the sample period with
units of 1/10ths of km/h. For a virtual zone (one created using AND and/or OR
Boolean functions), the value of 65535 shall be returned as it is not straight
forward to calculate speed from logically combined zones. For a volume of zero
during the sample period, the value of 65535 shall be returned to represent an
invalid or missing value. A missing value is reported when the zoneStatus
returned indicates no other status values apply for the entire sampling period.
Values 2551 through 65534 are reserved for future use.
<Parameter Type> Status 
<Object Identifier> 1.3.6.1.4.1.1206.4.2.4.3.4.1.6"
::= { sampleDataEntry 6 }

-- 5.4.4.7 Sample Zone Status
sampleZoneStatus  OBJECT-TYPE
SYNTAX  INTEGER {
                 other (1),
                 oK (2),
                 initializing (3),
                 noActivity (4),
                 maxPresence (5),
                 configurationError (6),
                 erraticCounts (7),
                 disabled (8),
                 overrideActive (9),
                 sensorFailure (10),
                 inputDataIntegrity (11),
                 poorContrast (12),
                 detectionAutoSuspended (13),
                 pairedZoneFault (14) }
MAX-ACCESS  read-only
STATUS  current
DESCRIPTION 
"<Definition> Detailed status returned as result of diagnostics, as follows:
      Value       Meaning
      other(1) - Indicates an error has occurred within the TSS for which
      there is no defined definition within this data element.
      oK(2) - Indicates no other status values apply.
      initializing(3) - Indicates an initialization or diagnostics procedure
      is in-progress.
      noActivity(4) - Indicates no activity condition.
      maxPresence(5) - Indicates max presence condition.
      configurationError(6) - Indicates an error within the TSS
      configuration setup.
      erraticCounts(7 )- Indicates erratic counts.
      disabled(8) - Indicates that the zone is disabled.
      overrideActive(9) - Indicates an override is active.
      sensorFailure(10) - Indicates a sensing element failure.
      inputDataIntegrity(11) - indicates input values are not sufficient to
      determine detector data accurately (e.g., bad communications, invalid
      video for machine vision).
      poorContrast(12) - Indicates insufficient contrast error condition.
      detectionAutoSuspended(13) - Indicates that the detection zone was
      automatically disabled by the TSS (e.g., camera is on a PTZ and
      was moved).
      pairedZoneFault(14) - Indicates that there was no problem with this
      zone, but a zone that it is paired with had a fault. This may affect
      the accuracy of data reported by this zone.
If a condition occurs during the sample period, then that state remains for the
duration of that sample period. If multiple conditions occur during a sample
period, the last reported condition, other than OK, is retained.
<Parameter Type> Status 
<Object Identifier> 1.3.6.1.4.1.1206.4.2.4.3.4.1.7"
::= { sampleDataEntry 7 }

-- 5.4.4.8 Sample Sequence Number
sampleSequenceNumber OBJECT-TYPE
SYNTAX  Integer32 (0..65535)
UNITS   "historic data entries"
MAX-ACCESS  read-only
STATUS  current
DESCRIPTION 
"<Definition> The data sample's sequence number, used to determine the
appropriate order of samples for a particular zone. All data from the same
sampling period have the same historical sequence number (all classes from the
same period have the same sequence number). 
<Parameter Type> Status 
<Object Identifier> 1.3.6.1.4.1.1206.4.2.4.3.4.1.8"
::= { sampleDataEntry 8 }

-- 5.4.4.9 Sample End Time Stamp
sampleEndTimeStamp OBJECT-TYPE
SYNTAX     ITSTimeStamp
MAX-ACCESS read-only
STATUS     current
DESCRIPTION 
"<Definition> Indicates the value of fdClockUtcTime when this data collection
period ended. 
<Parameter Type> Status 
<Object Identifier> 1.3.6.1.4.1.1206.4.2.4.3.4.1.3"
DEFVAL { '0000000000000000'H }
::= { sampleDataEntry 9 }

-- 5.4.5 Zone Class Table
zoneClassTable OBJECT-TYPE
SYNTAX     SEQUENCE OF ZoneClassTableEntry
MAX-ACCESS not-accessible
STATUS     current
DESCRIPTION 
"<Definition> This is a table that allows the TSS to associate a label for each
class within each zone. These are most likely set by the manufacturer; however
the manufacturer may allow the user to modify these through means outside of
this protocol.
<TableType> static
<Object Identifier> 1.3.6.1.4.1.1206.4.2.4.3.5"
::= { tssDataCollection 5 }

zoneClassTableEntry OBJECT-TYPE
SYNTAX     ZoneClassTableEntry
MAX-ACCESS not-accessible
STATUS     current
DESCRIPTION 
"<Definition> Table containing entries for the class labels for each zone. 
<Object Identifier> 1.3.6.1.4.1.1206.4.2.4.3.5.1"
INDEX { sensorZoneNumber, sampleZoneClass }
::= { zoneClassTable 1 }

ZoneClassTableEntry ::= SEQUENCE {
      zoneClassLabel      SnmpAdminString }

-- 5.4.5.1 Zone Class Label
zoneClassLabel  OBJECT-TYPE
SYNTAX     SnmpAdminString
MAX-ACCESS read-only
STATUS     current
DESCRIPTION
"<Definition> The textual label assigned to the indicated class within the
indicated zone to aid in identifying the data contained within the class. 
<Parameter Type> Status 
<Object Identifier> 1.3.6.1.4.1.1206.4.2.4.3.5.1.1"
::= { zoneClassTableEntry 1 }

-- 5.5 INDUCTIVE LOOP DETECTOR OBJECTS
tssInductiveLoop OBJECT-IDENTITY
STATUS  current
DESCRIPTION
"This node contains the configuration objects specific to inductive loop
detectors. These objects set up physical parameters on the detector that are
controlled on a per output basis. These objects are only valid for the zones
that map directly to an output on the detector. Zone 1 maps to output 1 and
Zone 2 maps to output 2 on a two-channel sensor unit and Zone 3 maps to output
3, and Zone 4 maps to output 4 on a four-channel sensor unit. For inductive
loop detectors, the term 'channel' is often used to refer to an 'output'.
<Object Identifier> 1.3.6.1.4.1.1206.4.2.4.4"
::= { tss 4 }

-- 5.5.1 Loop System Setup Table
loopSensorSetupTable OBJECT-TYPE
SYNTAX  SEQUENCE OF LoopSensorSetupEntry
MAX-ACCESS  not-accessible
STATUS  current
DESCRIPTION 
"<Definition> This table contains inductive loop detector sensor zone
parameters. The number of rows in this table equals the number of loop
detectors (this is typically the number of maxSensorZones but sensor zones not
associated with loop detectors are not present in the table). This table
contains the configuration objects specific to inductive loop detectors. These
objects set up physical parameters on the detector that are controlled on a per
output basis. A zone maps directly to an output on an inductive loop detector -
Zone 1 maps to output 1, Zone 2 maps to output 2, and, on a four-channel sensor
unit, Zone 3 maps to output 3 and Zone 4 maps to output 4. Virtual zones may be
supported once all physical outputs have had sensor zones mapped to them. Table
rows are set by the manufacturer, and row creation/deletion is not supported.
<TableType> static
<Object Identifier> 1.3.6.1.4.1.1206.4.2.4.4.1"
::= { tssInductiveLoop 1 }

loopSensorSetupEntry OBJECT-TYPE
SYNTAX  LoopSensorSetupEntry
MAX-ACCESS  not-accessible
STATUS  current
DESCRIPTION 
"<Definition> Row in table that contains inductive loop detector sensor zone
parameters. The number of rows equals the number of loop detectors. Table
rows are set by the manufacturer, and row creation/deletion is not supported.
<Object Identifier> 1.3.6.1.4.1.1206.4.2.4.4.1.1"

INDEX { sensorZoneNumber }
::= { loopSensorSetupTable 1 }

LoopSensorSetupEntry ::= SEQUENCE {
      zoneSensitivityMode     INTEGER,
      zoneSensitivity         OCTET STRING,
      zoneFrequencyRange      ITSUByteString,
      sensorZoneLoopLayout    INTEGER }

-- 5.5.1.1 Zone Sensitivity Mode
zoneSensitivityMode  OBJECT-TYPE
SYNTAX     INTEGER { 
                 deltaL (1),
                 deltaLOverSqrtL (2),
                 deltaLOverL (3) }
MAX-ACCESS read-only
STATUS     current
DESCRIPTION 
"<Definition> Sensitivity mode in use. This is a characteristic of the loop
detector being used.
<Format>
1 - change in inductance
2 - change in inductance divided by the squareroot of inductance
3 - change in inductance divided by inductance
<Parameter Type> Status 
<Object Identifier> 1.3.6.1.4.1.1206.4.2.4.4.1.1.1"
::= { loopSensorSetupEntry 1 }

-- 5.5.1.2 Zone Sensitivity
zoneSensitivity  OBJECT-TYPE
SYNTAX     OCTET STRING (SIZE(2))
MAX-ACCESS read-write
STATUS     current
DESCRIPTION 
"<Definition> This object indicates the sensitivity configuration for the zone. 
<Format>
The high-order bit acts as an encoding flag; the remaining 15 bits are encoded
as a two-octet non-negative-binary-integer according to the rules of OER. When
the high-order bit is zero, the following rules apply

     value        Meaning
      0        Zone OFF (Disabled) (LSB)
      1        Detect ?L = 512 nanoHenries or ?L/L = 0.64%
      2        Detect ?L = 256 nanoHhenries or ?L/L = 0.32%
      3        Detect ?L = 128 nanoHenries or ?L/L = 0.16%
      4        Detect ?L = 64 nanoHenries or ?L/L = 0.08%
      5        Detect ?L = 32 nanoHenries or ?L/L = 0.04%
      6        Detect ?L = 16 nanoHenries or ?L/L = 0.02%
      7        Detect ?L = 8 nanoHenries or ?L/L = 0.01%
  8-32767      Reserved

These sensitivity definitions are equal with a loop inductance of 80
microhenry. A detector need not support all of these settings. However, the
sensitivities it does support are required to conform with these definitions,
e.g. a sensitivity setting of 3 is always 128 nanohenry or 0.16% with an 80
microhenry loop. 

A value of 0xFFFF =(65535) shall indicate invalid data or not a physical zone.
Otherwise, if the high-order bit of the first octet is set, the remaining bits
indicate the sensitivity in nanohenry or one-thousands of a percent (depending
on the value in zoneSensitivityMode), e.g. a value of 0x8E42 = (high-bit set +
3650) and represents either 3650 nonohenry or 3.650%. 
<Informative> The value assignments are summarized in the table below:

+-------+-------------+----------------------+
|       |  Change in  | Change in inductance |
| Value | inductance  |    / inductance      |
        | (nanohenry) |         (%)          | 
+-------+-------------+----------------------+
|   0   |        Zone OFF (Disabled)         |
+-------+-------------+----------------------+
|   1   |     512     |        0.64%         |
|   2   |     256     |        0.32%         |
|   3   |     128     |        0.16%         |
|   4   |      64     |        0.08%         |
|   5   |      32     |        0.04%         |
|   6   |      16     |        0.02%         |
|   7   |       8     |        0.01%         |
+-------+-------------+----------------------+
|8-32767|             <Reserved>             |
+-------+-------------+----------------------+
|0x8000-| 0 to 32,767 |     0 to 32.767%     |
|0x8FFE |             |                      |
+-------+-------------+----------------------+
|0xFFFF | invalid data or not a physical zone|
+-------+------------------------------------+
<Parameter Type> Configuration 
<Object Identifier> 1.3.6.1.4.1.1206.4.2.4.4.1.1.2"
::= { loopSensorSetupEntry 2 }

-- 5.5.1.3 Zone Frequency Range
zoneFrequencyRange  OBJECT-TYPE
SYNTAX     ITSUByteString (SIZE(1))
MAX-ACCESS read-write
STATUS     current
DESCRIPTION
"<Definition> The frequency level. Implementations must support at least four
levels and may support up to eight levels, numbered sequentially from zero
As the frequency level increases the operation frequency shall increase. The
loop frequency at level zero (0) shall be less than 88% of the loop frequency
at the highest level. A value of 255 shall be returned to represent invalid
data or not a physical zone. Values of 8 through 254 are reserved.
<Parameter Type> Configuration 
<Object Identifier> 1.3.6.1.4.1.1206.4.2.4.4.1.1.3"
::= { loopSensorSetupEntry 3 }

-- 5.5.1.4 Sensor Zone Loop Layout
sensorZoneLoopLayout  OBJECT-TYPE
SYNTAX     INTEGER {
                 other (1),
                 oneSixBySixLoopOneLane (2),
                 twoSixBySixLoopsOneLane (3),
                 threeSixBySixLoopsOneLane (4),
                 fourSixBySixLoopsOneLane (5),
                 oneLongLoopOneLane (6),
                 oneSixBySixLoopMultipleLanes (7) }
MAX-ACCESS read-write
STATUS     current
DESCRIPTION
"<Definition> The zone configuration provides for standardized sensor loop
layouts typically used in roadway applications.
      other(1) - Used for special loop configurations and layouts.
      oneSixBySixLoopOneLane(2) - Used when there is one six-foot by six-
      foot loop in one travel lane.
      twoSixBySixLoopsOneLane(3) - Used when there are two six-foot by six-
      foot loops in one travel lane. 
      threeSixBySixLoopsOneLane(4) - Used when there are three six-foot by
      six-foot loops in one travel lane.
      fourSixBySixLoopsOneLane(5) - Used when there are four six-foot by six-
      foot loops in one travel lane.
      oneLongLoopOneLane(6) - Used when there is one loop in one travel
      lane that exceeds six-feet in length.
      oneSixBySixLoopMultipleLanes(7) - Used when there is one six-foot by
      six-foot loop in each of more than one travel lane.
<Parameter Type> Configuration 
<Object Identifier> 1.3.6.1.4.1.1206.4.2.4.4.1.1.4"
::= { loopSensorSetupEntry 4 }

-- 5.5.2 Loop Output Conditioning Table
loopOutputConditioningTable  OBJECT-TYPE
SYNTAX  SEQUENCE OF LoopOutputConditioningEntry
MAX-ACCESS  not-accessible
STATUS  deprecated
DESCRIPTION 
"<Definition> Each table row contains objects for configuring inductive loop
detector sensor zone outputs. The number of rows in this table does not exceed
maxSensorZones. Table rows are set by the manufacturer, and row
creation/deletion is not supported.
<Superseded by> outputConditioningTable. If this object is supported, it must
contain data that is consistent with the outputConditioningTable.
<Informative> This object was deprecated in NTCIP 1209 v02.
<TableType> static
<Object Identifier> 1.3.6.1.4.1.1206.4.2.4.4.2"
::= { tssInductiveLoop 2 }

loopOutputConditioningEntry  OBJECT-TYPE
SYNTAX  LoopOutputConditioningEntry
MAX-ACCESS  not-accessible
STATUS  deprecated
DESCRIPTION 
"<Definition> Each table row contains inductive loop detector sensor zone
output conditioning parameters. 
<Superseded by> outputConditioningEntry. If this object is supported, it must
contain data that is consistent with its superseding object.
<Informative> This object was deprecated in NTCIP 1209 v02.
<Object Identifier> 1.3.6.1.4.1.1206.4.2.4.4.2.1"

INDEX { sensorZoneNumber }
::= { loopOutputConditioningTable 1 }

LoopOutputConditioningEntry ::= SEQUENCE {
      zoneOutputMode         INTEGER,
      zoneMaxPresenceTime    Integer32,
      zoneOutputDelayTime    Integer32,
      zoneOutputExtendTime    Integer32,
      zoneOutputExtendEnable    OCTET STRING,
      zoneOutputDelayEnable     OCTET STRING }

-- 5.5.2.1 Zone Output Mode
zoneOutputMode  OBJECT-TYPE
SYNTAX     INTEGER {
                 other (1),
                 pulse (2),
                 presence (3) }
MAX-ACCESS read-write
STATUS     deprecated
DESCRIPTION 
"<Definition> This object sets the length of the output during a detect
condition. These detect outputs are described as follows:
      Other - an output mode other than that defined in NTCIP 1209.
      Pulse - a pulse of 125ms (?25ms) is output when a vehicle is
      detected.
      Presence - the output lasts the duration of a detect condition or
      until the detector tunes out the detect signal.
A value of 255 shall be returned to represent invalid data.
<Parameter Type> Configuration 
<Superseded by> sensorZoneOutputMode. If this object is supported, it must
contain data that is consistent with its superseding object.
<Informative> This object was deprecated in NTCIP 1209 v02.
<Object Identifier> 1.3.6.1.4.1.1206.4.2.4.4.2.1.1"
::= { loopOutputConditioningEntry 1 }

-- 5.5.2.2 Zone Max Presence Feature Time
zoneMaxPresenceTime  OBJECT-TYPE
SYNTAX     Integer32 (0..65535)
UNITS      "seconds"
MAX-ACCESS read-write
STATUS     deprecated
DESCRIPTION 
"<Definition> This object sets the maximum time that the zone holds presence
before retuning. Values of 1 to 65534 seconds are available. A value of 0
disables this timer and prevents a sensor zone occupancy from being tuned out
at the end of a specific time. A value of 65,535 represents invalid data.
<Parameter Type> Configuration 
<Superseded by> sensorZoneMaxPresenceTime. If this object is supported, it must
contain data that is consistent with its superseding object.
<Informative> This object was deprecated in NTCIP 1209 v02.
<Object Identifier> 1.3.6.1.4.1.1206.4.2.4.4.2.1.2"
::= { loopOutputConditioningEntry 2 }

-- 5.5.2.3 Zone Output Delay Time
zoneOutputDelayTime  OBJECT-TYPE
SYNTAX     Integer32 (0..65535)
UNITS      "deciseconds"
MAX-ACCESS read-write
STATUS     deprecated
DESCRIPTION 
"<Definition> The output for the zone is delayed from start of sensor zone
occupancy by the time specified (tenths of a second:  00.0 to 6553.5 sec). For
the output to actually switch, the sensor zone occupancy is required to be
continuous and still be present at the end of the delay time.
<Parameter Type> Configuration 
<Superseded by> sensorZoneOutputDelayTime. If this object is supported, it must
contain data that is consistent with its superseding object.
<Informative> This object was deprecated in NTCIP 1209 v02.
<Object Identifier> 1.3.6.1.4.1.1206.4.2.4.4.2.1.3"
REFERENCE
"NEMA TS2 Clause 3.5.5.5.4.c and 6.5.2.24.1"  
::= { loopOutputConditioningEntry 3 }

-- 5.5.2.4 Zone Output Extend Time
zoneOutputExtendTime  OBJECT-TYPE
SYNTAX     Integer32 (0..65535)
UNITS      "deciseconds"
MAX-ACCESS read-write
STATUS     deprecated
DESCRIPTION 
"<Definition> The output for the zone is extended, after the end of the period
in which the sensor zone is occupied, by the amount of time specified (tenths
of a second: 00.0 to 6553.5 sec).
<Parameter Type> Configuration 
<Superseded by> sensorZoneOutputExtendTime. If this object is supported, it
must contain data that is consistent with its superseding object.
<Informative> This object was deprecated in NTCIP 1209 v02.
<Object Identifier> 1.3.6.1.4.1.1206.4.2.4.4.2.1.4"
REFERENCE
"NEMA TS2 Clause 3.5.5.5.4.d and 6.5.2.24.2"  
::= { loopOutputConditioningEntry 4 }

-- 5.5.2.5 Zone Output Extend Enable
zoneOutputExtendEnable  OBJECT-TYPE
SYNTAX     OCTET STRING (SIZE(1))
MAX-ACCESS read-write
STATUS     deprecated
DESCRIPTION  
"<Definition> A bit-mapped value as defined below to enable and disable the
extend time for the sensor zone output, as follows:
<Format>
bit 7    0 = NO, 1 = YES            HIGH on output 1 Arming Pin to enable
                                    extend time for the zone (MSB),
bit 6    0 = NO, 1 = YES            HIGH on output 2 Arming Pin to enable
                                    extend time for the zone,
bit 5    0 = NO, 1 = YES            HIGH on output 3 Arming Pin to enable
                                    extend time for the zone,
bit 4    0 = NO, 1 = YES            HIGH on output 4 Arming Pin to enable
                                    extend time for the zone,
bit 3    0 = NO, 1 = YES            LOW on output 1 Arming Pin to enable
                                    extend time for the zone (MSB),
bit 2    0 = NO, 1 = YES            LOW on output 2 Arming Pin to enable
                                    extend time for the zone,
bit 1    0 = NO, 1 = YES            LOW on output 3 Arming Pin to enable
                                    extend time for the zone,
bit 0    0 = NO, 1 = YES            LOW on output 4 Arming Pin to enable
                                    extend time for the zone (LSB).
Extend time is always enabled for the zone if all bits are zero (0).
<Parameter Type> Configuration 
<Superseded by> sensorZoneOutputExtendMode and sensorZoneOutputExtendEnables.
If this object is supported, it must contain data that is consistent with its
superseding objects.
<Informative> This object was deprecated in NTCIP 1209 v02.
<Object Identifier> 1.3.6.1.4.1.1206.4.2.4.4.2.1.5"
REFERENCE
"NEMA TS2 Clause 6.5.2.8.7, 6.5.2.24 and 6.5.2.25.6"
::= { loopOutputConditioningEntry 5 }

-- 5.5.2.6 Zone Output Delay Enabled
zoneOutputDelayEnable  OBJECT-TYPE
SYNTAX     OCTET STRING (SIZE(1))
MAX-ACCESS read-write
STATUS     deprecated
DESCRIPTION  
"<Definition> A bit-mapped value as defined below to enable and disable the
delay time for the sensor zone output, as follows:
<Format>
bit 7    0 = NO, 1 = YES            HIGH on output 1 Arming Pin to enable
                                    delay time for the zone (MSB),
bit 6    0 = NO, 1 = YES            HIGH on output 2 Arming Pin to enable
                                    delay time for the zone,
bit 5    0 = NO, 1 = YES            HIGH on output 3 Arming Pin to enable
                                    delay time for the zone,
bit 4    0 = NO, 1 = YES            HIGH on output 4 Arming Pin to enable
                                    delay time for the zone,
bit 3    0 = NO, 1 = YES            LOW on output 1 Arming Pin to enable delay
                                    time for the zone (MSB),
bit 2    0 = NO, 1 = YES            LOW on output 2 Arming Pin to enable delay
                                    time for the zone,
bit 1    0 = NO, 1 = YES            LOW on output 3 Arming Pin to enable delay
                                    time for the zone,
bit 0    0 = NO, 1 = YES            LOW on output 4 Arming Pin to enable delay
                                    time for the zone,
Delay time is always enabled for the zone if all bits are zero (0).
<Parameter Type> Configuration 
<Superseded by> sensorZoneOutputDelayMode and sensorZoneOutputDelayEnables. If
this object is supported, it must contain data that is consistent with its
superseding objects.
<Informative> This object was deprecated in NTCIP 1209 v02.
<Object Identifier> 1.3.6.1.4.1.1206.4.2.4.4.2.1.6"
REFERENCE
"NEMA TS2 Clause 6.5.2.8.7, 6.5.2.24 and 6.5.2.25.6"
::= { loopOutputConditioningEntry 6 }

-- 5.5.3 Loop System Status Table
loopSystemStatusTable  OBJECT-TYPE
SYNTAX  SEQUENCE OF LoopSystemStatusEntry
MAX-ACCESS  not-accessible
STATUS  current
DESCRIPTION 
"<Definition> This table contains inductive loop detector sensor zone status
parameters. The number of rows in this table does not exceed maxSensorZones.
This table contains instantaneous zone status objects specific to inductive
loop detectors. The zoneDetectStatus object may be used by external systems for
doing detailed traffic analysis. A zone maps directly to an output on an
inductive loop detector - Zones 1 maps to output 1, Zone 2 maps to output 2,
and, on a four output inductive loop detector, Zone 3 maps to output 3 and Zone
4 maps to output 4. Table rows are set by the manufacturer, and row
creation/deletion is not supported.
<TableType> static
<Object Identifier> 1.3.6.1.4.1.1206.4.2.4.4.3"
::= { tssInductiveLoop 3 }

loopSystemStatusEntry OBJECT-TYPE
SYNTAX  LoopSystemStatusEntry
MAX-ACCESS  not-accessible
STATUS  current
DESCRIPTION 
"<Definition> Rows in this table contain inductive loop detector sensor zone
status parameters. The number of rows in this table does not exceed
maxSensorZones. Table rows are set by the manufacturer, and row
creation/deletion is not supported. 
<Object Identifier> 1.3.6.1.4.1.1206.4.2.4.4.3.1"
INDEX { sensorZoneNumber }
::= { loopSystemStatusTable 1 }

LoopSystemStatusEntry ::= SEQUENCE {
      zoneInductance                Integer32,
      zoneFrequency                 Integer32,
      zoneInductanceChange          Integer32,
      zoneFaultHistory              ITSBitmap,
      zoneFaultCount                Integer32,
      zonePercentInductanceChange   Integer32 }

-- 5.5.3.1 Zone Inductance
zoneInductance  OBJECT-TYPE
SYNTAX     Integer32 (0..65535)
UNITS      "tenths of microhenry"
MAX-ACCESS read-only
STATUS     current
DESCRIPTION 
"<Definition> The detector unit calculates the inductance of the loop attached
to the zone. The resolution is in tenths of a microhenry. For example, 852.4
microhenry is represented as 8524. Resolution does not imply accuracy, refer to
manufacturers' data sheet. A value of 65535 shall be returned to represent
invalid data or not a physical zone.
<Parameter Type> Status 
<Object Identifier> 1.3.6.1.4.1.1206.4.2.4.4.3.1.1"
::= { loopSystemStatusEntry 1 }

-- 5.5.3.2 Zone Frequency
zoneFrequency  OBJECT-TYPE
SYNTAX     Integer32 (0..16777216)
UNITS      "tenths of hertz"
MAX-ACCESS read-only
STATUS     current
DESCRIPTION  
"<Definition> This is the frequency of the inductive loop attached to the zone.
The frequency resolution is one-tenth hertz. For example, 53240 Hz is
represented as 532400. Resolution does not imply accuracy, refer to
manufacturers' data sheet. A value of 16777216 shall be returned to represent
invalid data or not a physical zone.
<Parameter Type> Status 
<Object Identifier> 1.3.6.1.4.1.1206.4.2.4.4.3.1.2"
::= { loopSystemStatusEntry 2 }

-- 5.5.3.3 Zone Inductance Change
zoneInductanceChange  OBJECT-TYPE
SYNTAX     Integer32 (0..8388608)
UNITS      "nanohenry"
MAX-ACCESS read-only
STATUS     current
DESCRIPTION  
"<Definition> The maximum inductance change seen since the last start of sensor
zone occupancy is returned. The resolution is to one nanohenry. Resolution does
not imply accuracy.
<Parameter Type> Status 
<Object Identifier> 1.3.6.1.4.1.1206.4.2.4.4.3.1.3"
::= { loopSystemStatusEntry 3 }

-- 5.5.3.4 Zone Fault History
zoneFaultHistory  OBJECT-TYPE
SYNTAX     ITSBitmap (SIZE (1))
MAX-ACCESS read-only
STATUS     current
DESCRIPTION  
"<Definition> A bit-mapped value representing the history of faults in Zone
since the last unit reset.
<Format>
Bit   Meaning
 0    Indicates that a current fault exists on the loop connected to the zone
 1    Indicates that the loop connected to the zone is open or this was the 
        last fault. (May be also be called a Maximum Presence fault by 
        external units.)
 2    Indicates that the loop connected to the zone is shorted or this was 
        the last fault. (May also be called a No Activity fault by external
        units.)
 3    Indicates that the loop inductance of the loop connected to the zone is 
        currently ? ?25% of reference or this was the last fault. (May also be 
        called a Erratic Count fault by external units.)
4..6  Reserved
 7    Indicates that data for this value is invalid data or this is not a 
        physical zone
<Parameter Type> Status 
<Object Identifier> 1.3.6.1.4.1.1206.4.2.4.4.3.1.4"
::= { loopSystemStatusEntry 4 }

-- 5.5.3.5 Zone Fault Count
zoneFaultCount  OBJECT-TYPE
SYNTAX     Integer32 (0..255)
UNITS      "faults"
MAX-ACCESS read-only
STATUS     current
DESCRIPTION 
"<Definition> Number of faults in the zone since the last unit reset. These
faults include open circuit; short circuit and ?25% drift faults. The fault
count may also include faults other than those defined in NTCIP 1209. The count
after 255 is 255.
<Parameter Type> Status 
<Informative> This is similar to a zero-based counter except that the value
sticks at 255 and never loops.
<Object Identifier> 1.3.6.1.4.1.1206.4.2.4.4.3.1.5"
::= { loopSystemStatusEntry 5 }

-- 5.5.3.6 Zone Percent Inductance Change
zonePercentInductanceChange  OBJECT-TYPE
SYNTAX     Integer32 (0..100000)
UNITS      "millipercent"
MAX-ACCESS read-only
STATUS     current
DESCRIPTION  
"<Definition> The maximum inductance change seen since the last start of sensor
zone occupancy is returned. The resolution is to one one-thousandth of a
percent. Resolution does not imply accuracy. For example a change of 0.1
percent would be represented as 100.
<Parameter Type> Status 
<Object Identifier> 1.3.6.1.4.1.1206.4.2.4.4.3.1.6"
::= { loopSystemStatusEntry 6 }

-- 5.6 MACHINE VISION OBJECTS
tssMachineVision OBJECT-IDENTITY
STATUS current
DESCRIPTION
"This node contains the configuration objects specific to machine vision
detectors.
<Object Identifier> 1.3.6.1.4.1.1206.4.2.4.5"
::={tss 5}

-- 5.6.1 Maximum Camera Count
maxCameraCount  OBJECT-TYPE
SYNTAX     Integer32 (1..255)
MAX-ACCESS read-only
STATUS     current
DESCRIPTION
"<Definition> This is the maximum number of machine vision cameras supported by
the system.
<Parameter Type> Status 
<Object Identifier> 1.3.6.1.4.1.1206.4.2.4.5.1"
::= { tssMachineVision 1 }

-- 5.6.2 Machine Vision Camera Table
machineVisionCameraTable  OBJECT-TYPE
SYNTAX  SEQUENCE OF MachineVisionCameraEntry
MAX-ACCESS  not-accessible
STATUS  current
DESCRIPTION
"<Definition> This table contains camera parameters. The number of rows in this
table shall equal maxCameraCount. This table contains the configuration objects
specific to machine vision cameras. Table rows are set by the manufacturer, and
row creation/deletion is not supported.
<TableType>  Static
<Informative> Prior to v03, this object stated that the number of rows would
not exceed maxCameraCount; the number of rows is now required to be equal.
<Object Identifier> 1.3.6.1.4.1.1206.4.2.4.5.2"
::= { tssMachineVision 2 }

machineVisionCameraEntry OBJECT-TYPE
SYNTAX  MachineVisionCameraEntry
MAX-ACCESS  not-accessible
STATUS  current
DESCRIPTION
"<Definition> Row in table that contains machine vision camera parameters. The
number of rows in this table shall equal maxCameraCount. Table rows are set by
the manufacturer, and row creation/deletion is not supported. 
<Informative> Prior to v03, this object stated that the number of rows would
not exceed maxCameraCount; the number of rows is now required to be equal.
<Object Identifier> 1.3.6.1.4.1.1206.4.2.4.5.2.1"
INDEX { cameraNumber }
::= { machineVisionCameraTable 1 }

MachineVisionCameraEntry ::= SEQUENCE {
      cameraNumber                  Integer32,
      cameraNameLabel               SnmpAdminString,
      imageReceptionDiagnostic      Integer32,
      cameraDetectionState          INTEGER,
      zoneListForCamera             TssBitmap256,
      baselineImage                 INTEGER,
      snapshotImage                 INTEGER,
      cameraImageFormat             ITSBitmap,
      zoneListForCameraV3           ITSBitmap }

-- 5.6.2.1 Camera Number
cameraNumber  OBJECT-TYPE
SYNTAX     Integer32 (1..255)
MAX-ACCESS read-only
STATUS     current
DESCRIPTION
"<Definition> The numerical label or number of the machine vision camera. This
number shall not exceed the maxCameraCount data element value.
<Parameter Type> Status 
<Object Identifier> 1.3.6.1.4.1.1206.4.2.4.5.2.1.1"
::= { machineVisionCameraEntry 1 }

-- 5.6.2.2 Camera Name Label
cameraNameLabel  OBJECT-TYPE
SYNTAX     SnmpAdminString
MAX-ACCESS read-write
STATUS     current
DESCRIPTION
"<Definition> A text string used to describe the camera name or location. A
camera name shall be a string length of less than 255 characters. 
<Parameter Type> Configuration 
<Object Identifier> 1.3.6.1.4.1.1206.4.2.4.5.2.1.2"
::= { machineVisionCameraEntry 2 }

-- 5.6.2.3 Image Reception Diagnostic
imageReceptionDiagnostic  OBJECT-TYPE
SYNTAX     Integer32 (0..100)
MAX-ACCESS read-only 
STATUS     current
DESCRIPTION
"<Definition> Image Reception Diagnostics is a measure of the health of the
image transition link from the camera to the machine vision processor. A value
of 100 means that all of the frames are being received and a value of 0 means
that frames are not being received. Values between 0 and 100 are manufacturer-
specific. This is used to track and debug transmission errors from the camera
to the machine vision processor. 
<Parameter Type> Status 
<Object Identifier> 1.3.6.1.4.1.1206.4.2.4.5.2.1.3"
::= { machineVisionCameraEntry 3 }

-- 5.6.2.4 Camera Detection State
cameraDetectionState  OBJECT-TYPE
SYNTAX     INTEGER {
                 detectionIsNotDisabled (1),
                 detectionIsDisabled (2) }
MAX-ACCESS read-write
STATUS     current
DESCRIPTION
"<Definition> A camera can be enabled/disabled so that it may be used for other
purposes such as surveillance. A disabled camera puts the associated zones in
failsafe mode. If a pole has been hit and the camera is no longer looking at
the traffic this can be used to put all the zones associated with that camera
in failsafe mode. It can also be used for pan-tilt-zoom camera to disable
detection so that the camera may be used for surveillance allowing the camera
to look at areas other than the detection area. Enabling the camera places all
the zones associated with that camera back into their defined detection mode.
<Parameter Type> Configuration 
<Object Identifier> 1.3.6.1.4.1.1206.4.2.4.5.2.1.4"
::= { machineVisionCameraEntry 4 }

-- 5.6.2.5 Zone List for Camera
zoneListForCamera  OBJECT-TYPE
SYNTAX     TssBitmap256
MAX-ACCESS read-only
STATUS     deprecated
DESCRIPTION
"<Definition> This is a bit map where a 1 in a bit position indicates that zone
is with the selected camera. The least significant bit (bit 0) of the first
octet (byte) shall represent zone 1 and bit 6 of the 32nd octet (byte) shall
represent zone 255. The most significant bit of the 32nd octet (byte) is
reserved and shall not be set.
<Parameter Type> Status 
<Superseded by> zoneListForCameraV3
<Informative> This object was deprecated in v03 due to the confusing bit order. 
<Object Identifier> 1.3.6.1.4.1.1206.4.2.4.5.2.1.5"
::= { machineVisionCameraEntry 5 }

-- 5.6.2.6 Baseline Image
baselineImage OBJECT-TYPE
SYNTAX     INTEGER {
                 notSupported (1),
                 supportedAndAvailable (2),
                 supportedButNotAvailable (3) }
MAX-ACCESS read-only
STATUS     current
DESCRIPTION
"<Definition> Determines whether the machine vision camera supports a baseline
image and the status of that image.
<Parameter Type> Status 
<Object Identifier> 1.3.6.1.4.1.1206.4.2.4.5.2.1.6"
::= { machineVisionCameraEntry 6 }

-- 5.6.2.7 Snapshot Image
snapshotImage  OBJECT-TYPE
SYNTAX     INTEGER {
                 notSupported (1),
                 supported (2) }
MAX-ACCESS read-only
STATUS     current
DESCRIPTION
"<Definition> This data element determines whether the machine vision camera
supports a snapshot image.
            notSupported(1) - Indicates that the machine vision camera does
            not support snapshot images.
            supported(2) - Indicates that the machine vision camera supports
            snapshot images.
<Parameter Type> Status 
<Object Identifier> 1.3.6.1.4.1.1206.4.2.4.5.2.1.7"
::= { machineVisionCameraEntry 7 }

-- 5.6.2.8 Camera Image Formats
cameraImageFormat  OBJECT-TYPE
SYNTAX     ITSBitmap (SIZE (4))
MAX-ACCESS read-only
STATUS     current
DESCRIPTION 
"<Definition> Defines the types of image formats that the machine vision camera
supports.
<Format>
Bit 31      The machine vision camera supports bitmap imagery;
Bit 30      The machine vision camera supports JPEG imagery;
Bits 0..29  Reserved.
<Parameter Type> Status 
<Object Identifier> 1.3.6.1.4.1.1206.4.2.4.5.2.1.8"
::= { machineVisionCameraEntry 8 }

-- 5.6.2.9 Zone List for Camera Version 3
zoneListForCameraV3  OBJECT-TYPE
SYNTAX      ITSBitmap (SIZE(32))
MAX-ACCESS  read-only
STATUS      current
DESCRIPTION
"<Definition> This is a bit map where a 1 in bit position x indicates that zone
x is associated with the selected camera. The meaning of Bit 0 is reserved. 
<Parameter Type> Status 
<Informative> For example, the value 0x70 followed by 31 0x00 octets indicates
that Zones 1, 2, and 3 are associated with the camera. 
<Object Identifier> 1.3.6.1.4.1.1206.4.2.4.5.2.1.9"
::= { machineVisionCameraEntry 9 }

-- 5.6.3 Image Zone Number
imageZoneNumber  OBJECT-TYPE	
SYNTAX     Integer32 (0..255)
MAX-ACCESS read-write
STATUS     current
DESCRIPTION
"<Definition> The numerical label or number representing the sensor zone number
that is associated with the image. A value of zero (0) indicates that no sensor
zone number is selected. When read, this data element returns the last value
written.
<Parameter Type> Configuration 
<Object Identifier> 1.3.6.1.4.1.1206.4.2.4.5.3"
::= { tssMachineVision 3 }

-- 5.6.4 Image Type
imageType  OBJECT-TYPE
SYNTAX     INTEGER {
                 snapshot (1),
                 baseline (2) }
MAX-ACCESS read-write
STATUS     current
DESCRIPTION 
"<Definition> This data element indicates the type of image to generate:  
            Snapshot(1) - Snapshot indicates to capture a current image to
            transmit;
            Baseline(2) - Baseline indicates to unse the baseline image used
            to set up the system for transfer.
<Parameter Type> Configuration 
<Object Identifier> 1.3.6.1.4.1.1206.4.2.4.5.4"
::= { tssMachineVision 4 }

-- 5.6.5 Image Overlay Type
imageOverlayType  OBJECT-TYPE
SYNTAX     INTEGER {
                 none (1),
                 thisZone (2),
                 allZones (3),
                 defaultOverlay (4) }
MAX-ACCESS read-write
STATUS     current
DESCRIPTION 
"<Definition> This data element sets the type of image overlay to generate:  
            none(1) - No overlay is generated in to the image;
            thisZone(2) - Indicates that an overlay is generated in the
            image indicating the location of this zone. The overlay specifics
            are manufacturer dependent;
            allZones(3) - Indicates that an overlay is generated in the
            image indicating the location of all zones associated with the
            camera. The overlay specifics are manufacturer dependent;
            defaultOverlay(4) - Indicates the manufacturer generates its
            default overlay in to the image.
<Parameter Type> Configuration 
<Object Identifier> 1.3.6.1.4.1.1206.4.2.4.5.5"
::= { tssMachineVision 5 }

-- 5.6.6 Image Format
imageFormat  OBJECT-TYPE
SYNTAX     INTEGER { 
                 bitmap (1),
                 jpeg (2) }
MAX-ACCESS read-write
STATUS     current
DESCRIPTION
"<Definition> Identifies what format to return the machine vision camera image
in.
<Parameter Type> Configuration 
<Object Identifier> 1.3.6.1.4.1.1206.4.2.4.5.6"
::= { tssMachineVision 6 }

-- 5.6.7 Image Quality
imageQuality  OBJECT-TYPE
SYNTAX     Integer32 (1..100)
MAX-ACCESS read-write
STATUS     current
DESCRIPTION
"<Definition> This data element is used to select the image quality. The
meaning varies based on the Image Format. A value of 100 selects the highest
quality available. A value of 1 selects the lowest quality available. Lower
quality may mean smaller more compressed images. Some image formats do not
support variable image quality so the value is ignored. If a manufacturer
supports only two image qualities for a specific image format then values 1 to
50 should select the lower quality while values 51 to 100 should select the
higher quality.
<Parameter Type> Configuration 
<Object Identifier> 1.3.6.1.4.1.1206.4.2.4.5.7"
::= { tssMachineVision 7 }

-- 5.6.8 Build Image
buildImageCmd  OBJECT-TYPE
SYNTAX     INTEGER {
                 buildImage (1),
                 cancelBuildInProgress (2) }
MAX-ACCESS read-write
STATUS     current
DESCRIPTION 
"<Definition> Writing the value buildImage to this data element commands the
sensor to build an image based on the preceding parameters. A read of this data
element always returns the last written. Values for this command are:
            buildImage(1) - This command shall cause the unit to build an
            image that can be read.
            cancelBuildInProgress(2) - This command shall cause the unit to
            cancel the current building process.
<Parameter Type> Configuration 
<Object Identifier> 1.3.6.1.4.1.1206.4.2.4.5.8"
::= { tssMachineVision 8 }

-- 5.6.9  Build Image Status
buildImageStatus  OBJECT-TYPE
SYNTAX     INTEGER {
                 noImage (1),
                 buildingImage (2),
                 imageReady (3),
                 genericError (4),
                 invalidParameter (5),
                 noCameraForZone (6),
                 multipleCamerasForZone (7),
                 imageReceiveError (8),
                 buildPending (9) }
MAX-ACCESS read-only
STATUS     current
DESCRIPTION 
"<Definition> Reading the value buildImageStatus from this data element yields
the status of the current image to be read:
            noImage(1) - No Image is available for reading. This is the
            initial state if the buildImageCmd command has not been issued;
            buildingImage(2) - The sensor is in the progress of building the
            image. It is not ready yet;
            imageReady(3) - The image is ready for transfer. The last build
            command completed successfully;
            genericError(4) - An error occurred generating an image and
            there is not a more descriptive status code available to describe
            it;
            invalidParameter(5) - One of the Image Setup Data parameters is
            invalid;
            noCameraForZone(6) - The zone selected does not have a camera
            associated with it;
            multipleCamerasForZone(7) - There is more than one camera
            associated with the zone. To build an image you must select a
            zone with one and only one camera;
            imageReceiveError(8) - The sensor is having trouble receiving an
            image from its camera. This could be bad sync or other
            transmission problems;
            buildPending(9) - The sensor cannot begin the requested build
            at this time. The build begins when the blocking condition
            was ended. This can occur if the current image is in use (e.g.,
            being transferred).
<Parameter Type> Status 
<Object Identifier> 1.3.6.1.4.1.1206.4.2.4.5.9"
::= { tssMachineVision 9 }


-- 5.7 OBJECT GROUPS
tssConformance OBJECT-IDENTITY 
STATUS current
DESCRIPTION
"<Definition> This node is an identifier used to manage the conformance for
TSS. 
<Object Identifier> 1.3.6.1.4.1.1206.4.2.4.127"
::= { tss 127 }

tssCompliances OBJECT-IDENTITY
STATUS       current
DESCRIPTION
"<Definition> A node for compliance statements for TSS objects.
<Object Identifier> 1.3.6.1.4.1.1206.4.2.4.127.1"
::= {tssConformance 1}

tssGroups OBJECT-IDENTITY
STATUS     current
DESCRIPTION
"<Definition> A node for group definitions related to the TSS MIB.
<Object Identifier> 1.3.6.1.4.1.1206.4.2.4.127.2"
::= { tssConformance 2 }


-- 5.7.1 TSS Core Group Version 1
tssCoreGroupV1 OBJECT-GROUP
OBJECTS { sensorSystemReset,
          sensorSystemStatus,
          sensorSystemOccupancyType,
          maxSensorZones,
          sensorZoneNumber,
          sensorZoneOptions,
          sensorZoneOptionsStatus,
          clockAvailable,
          maxOutputNumber,
          outputNumber,
          outputSensorZoneNumber,
          outputFailsafeMode,
          outputModeStatus,
          outputLabel,
          maxOutputGroups,
          outputGroupNumber,
          outputGroupOutputState }
STATUS  deprecated
DESCRIPTION
"<Definition> The core set of TSS objects required for all implementations of 
NTCIP 1209 v01.
<Object Identifier> 1.3.6.1.4.1.1206.4.2.4.127.2.1"
::= { tssGroups 1 }

-- 5.7.2 TSS Loop Group Version 1
tssLoopGroupV1 OBJECT-GROUP
OBJECTS { zoneSensitivityMode,
          zoneSensitivity,
          zoneFrequencyRange,
          zoneInductance,
          zoneFrequency,
          zoneInductanceChange,
          zoneFaultHistory,
          zoneFaultCount }
STATUS  deprecated
DESCRIPTION
"<Definition> The set of TSS objects required for TSS inductive loop 
management in NTCIP 1209 v03.
<Object Identifier> 1.3.6.1.4.1.1206.4.2.4.127.2.2"
::= { tssGroups 2 }

-- 5.7.3 TSS Sample Group Version 1
tssSampleGroupV1 OBJECT-GROUP
OBJECTS { sensorZoneSamplePeriod, 
          endTime,
          volumeData,
          percentOccupancy,
          zoneStatus,
          endTimeBuffer,
          volumeDataBuffer,
          percentOccupancyBuffer,
          zoneStatusBuffer }
STATUS  deprecated
DESCRIPTION
"<Definition> The set of TSS objects required for TSS sample management in 
NTCIP 1209 v03.
<Object Identifier> 1.3.6.1.4.1.1206.4.2.4.127.2.3"
::= { tssGroups 3 }

-- 5.7.4 TSS Speed Group Version 1
tssSpeedGroupV1 OBJECT-GROUP
OBJECTS { speedData,
          speedDataBuffer }
STATUS  deprecated
DESCRIPTION
"<Definition> The set of TSS objects required for TSS speed management in 
NTCIP 1209 v03.
<Object Identifier> 1.3.6.1.4.1.1206.4.2.4.127.2.4"
::= { tssGroups 4 }

-- 5.7.5 TSS And Logic Group Version 1
tssAndLogicGroupV1 OBJECT-GROUP
OBJECTS { sensorZoneAndOperator }
STATUS  current
DESCRIPTION
"<Definition> The set of TSS objects required for supporting AND logic in 
NTCIP 1209 v03.
<Object Identifier> 1.3.6.1.4.1.1206.4.2.4.127.2.5"
::= { tssGroups 5 }

-- 5.7.6 TSS Or Logic Group Version 1
tssOrLogicGroupV1 OBJECT-GROUP
OBJECTS { sensorZoneOrOperator }
STATUS  current
DESCRIPTION
"<Definition> The set of TSS objects required for supporting OR logic in 
NTCIP 1209 v03.
<Object Identifier> 1.3.6.1.4.1.1206.4.2.4.127.2.6"
::= { tssGroups 6 }

-- 5.7.7 TSS Delay Logic Group Version 1
tssDelayLogicGroupV1 OBJECT-GROUP
OBJECTS { zoneOutputMode,
          zoneMaxPresenceTime,
          zoneOutputDelayEnable,
          zoneOutputDelayTime }
STATUS  deprecated
DESCRIPTION
"<Definition> The set of TSS objects required for supporting delay logic in 
NTCIP 1209 v03.
<Object Identifier> 1.3.6.1.4.1.1206.4.2.4.127.2.7"
::= { tssGroups 7 }

-- 5.7.8 TSS Extend Logic Group Version 1
tssExtendLogicGroupV1 OBJECT-GROUP
OBJECTS { zoneOutputMode,
          zoneMaxPresenceTime,
          zoneOutputExtendTime,
          zoneOutputExtendEnable }
STATUS  deprecated
DESCRIPTION
"<Definition> The set of TSS objects required for supporting delay logic in 
NTCIP 1209 v03.
<Object Identifier> 1.3.6.1.4.1.1206.4.2.4.127.2.8"
::= { tssGroups 8 }

-- 5.7.9 TSS Sensor Label Group Version 1
tssSensorLabelGroupV1 OBJECT-GROUP
OBJECTS { sensorZoneLabel }
STATUS  current
DESCRIPTION
"<Definition> The set of TSS objects required for supporting sensor labels in 
NTCIP 1209 v03.
<Object Identifier> 1.3.6.1.4.1.1206.4.2.4.127.2.9"
::= { tssGroups 9 }

-- 5.7.10 TSS Core Group Version 2
tssCoreGroupV2 OBJECT-GROUP
OBJECTS { sensorSystemReset,
          sensorSystemStatus,
          sensorSystemOccupancyType,
          maxSensorZones,
          sensorZoneNumber,
          sensorZoneOptions,
          sensorZoneOptionsStatus,
          sensorZoneStatus,
          sensorZoneNoActivityFaultTime,
          sensorZoneMaxPresenceFaultTime,
          sensorZoneErraticCountsFaultTime,
          sensorZoneErraticCountsThreshold,
          clockAvailable,
          sensorTechnology,
          maxNumberOfCharacters,
          functionalCapabilities,
          sensorZoneOutputMode,
          maxOutputNumber,
          outputNumber,
          outputSensorZoneNumber,
          outputFailsafeMode,
          outputModeStatus,
          outputLabel,
          maxOutputGroups,
          outputGroupNumber,
          outputGroupOutputState }
STATUS  deprecated
DESCRIPTION
"<Definition> The core set of TSS objects required for all implementations of 
NTCIP 1209 v03.
<Object Identifier> 1.3.6.1.4.1.1206.4.2.4.127.2.10"
::= { tssGroups 10 }

-- 5.7.11 TSS Configuration Group Version 2
tssConfigGroupV2 OBJECT-GROUP
OBJECTS { pendingConfigurationFileName }
STATUS  deprecated
DESCRIPTION
"<Definition> The set of TSS objects required for TSS configuration management 
in NTCIP 1209 v03.
<Object Identifier> 1.3.6.1.4.1.1206.4.2.4.127.2.11"
::= { tssGroups 11 }

-- 5.7.12 TSS Loop Group Version 2
tssLoopGroupV2 OBJECT-GROUP
OBJECTS { zoneSensitivityMode,
          zoneSensitivity,
          zoneFrequencyRange,
          sensorZoneLoopLayout,
          zoneInductance,
          zoneFrequency,
          zoneInductanceChange,
          zoneFaultHistory,
          zoneFaultCount,
          zonePercentInductanceChange }
STATUS  current
DESCRIPTION
"<Definition> The set of TSS objects required for TSS inductive loop 
management in NTCIP 1209 v03.
<Object Identifier> 1.3.6.1.4.1.1206.4.2.4.127.2.12"
::= { tssGroups 12 }

-- 5.7.13 TSS Sample Group Version 2
tssSampleGroupV2 OBJECT-GROUP
OBJECTS { sensorZoneSamplePeriod, 
          maxSampleDataEntries,
          numSampleDataEntries,
          numSensorZoneClass,
          sampleEntryNum,
          sampleZoneClass,
          sampleEndTime,
          sampleVolumeData,
          samplePercentOccupancy,
          sampleZoneStatus,
          sampleSequenceNumber,
          zoneClassLabel }
STATUS  deprecated
DESCRIPTION
"<Definition> The set of TSS objects required for TSS sample management in 
NTCIP 1209 v03.
<Object Identifier> 1.3.6.1.4.1.1206.4.2.4.127.2.13"
::= { tssGroups 13 }

-- 5.7.14 TSS Speed Group Version 2
tssSpeedGroupV2 OBJECT-GROUP
OBJECTS { sensorZonePairedZoneSpacing,
          sensorZoneSpeedCorrectionFactor,
          sensorZoneAvgVehicleLength,
          sensorZoneLength,
          sensorZonePairedZone,
          sensorZonePairedZoneOptions,
          sensorZoneOutputSequenced,
          sampleSpeedData }
STATUS  current
DESCRIPTION
"<Definition> The set of TSS objects required for TSS speed management in 
NTCIP 1209 v03.
<Object Identifier> 1.3.6.1.4.1.1206.4.2.4.127.2.14"
::= { tssGroups 14 }

-- 5.7.15 TSS Video Group Version 2
tssVideoGroupV2 OBJECT-GROUP
OBJECTS { maxCameraCount, 
          cameraNumber,
          imageReceptionDiagnostic,
          zoneListForCamera }
STATUS  deprecated
DESCRIPTION
"<Definition> The set of TSS objects required for TSS video image processing 
management in NTCIP 1209 v03.
<Object Identifier> 1.3.6.1.4.1.1206.4.2.4.127.2.15"
::= { tssGroups 15 }

-- 5.7.16 TSS Delay Logic Group Version 2
tssDelayLogicGroupV2 OBJECT-GROUP
OBJECTS { sensorZoneMaxPresenceTime,
          sensorZoneOutputDelayTime,
          sensorZoneOutputDelayMode,
          sensorZoneOutputDelayEnables }
STATUS  deprecated
DESCRIPTION
"<Definition> The set of TSS objects required for supporting delay logic in 
NTCIP 1209 v03.
<Object Identifier> 1.3.6.1.4.1.1206.4.2.4.127.2.16"
::= { tssGroups 16 }

-- 5.7.17 TSS Extend Logic Group Version 2
tssExtendLogicGroupV2 OBJECT-GROUP
OBJECTS { sensorZoneMaxPresenceTime,
          sensorZoneOutputExtendTime,
          sensorZoneOutputExtendMode,
          sensorZoneOutputExtendEnables }
STATUS  deprecated
DESCRIPTION
"<Definition> The set of TSS objects required for supporting extend logic in 
NTCIP 1209 v03.
<Object Identifier> 1.3.6.1.4.1.1206.4.2.4.127.2.17"
::= { tssGroups 17 }

-- 5.7.18 TSS Arming Inputs Group Version 2
tssArmingInputsGroupV2 OBJECT-GROUP
OBJECTS { externalArmingInputs }
STATUS  deprecated
DESCRIPTION
"<Definition> The set of TSS objects required for supporting arming inputs in 
NTCIP 1209 v03.
<Object Identifier> 1.3.6.1.4.1.1206.4.2.4.127.2.18"
::= { tssGroups 18 }

-- 5.7.19 TSS Arming Outputs Group Version 2
tssArmingOutputsGroupV2 OBJECT-GROUP
OBJECTS { outputArmingEnables,
          outputArmingMode }
STATUS  deprecated
DESCRIPTION
"<Definition> The set of TSS objects required for supporting arming outputs in 
NTCIP 1209 v03.
<Object Identifier> 1.3.6.1.4.1.1206.4.2.4.127.2.19"
::= { tssGroups 19 }

-- 5.7.20 TSS Camera Label Group Version 2
tssCameraLabelGroupV2 OBJECT-GROUP
OBJECTS { cameraNameLabel }
STATUS  current
DESCRIPTION
"<Definition> The set of TSS objects required for supporting camera labels in 
NTCIP 1209 v03.
<Object Identifier> 1.3.6.1.4.1.1206.4.2.4.127.2.20"
::= { tssGroups 20 }

-- 5.7.21 TSS Image Group Version 2
tssImageGroupV2 OBJECT-GROUP
OBJECTS { baselineImage,
          snapshotImage,
          cameraImageFormat,
          imageZoneNumber,
          imageType,
          imageOverlayType,
          imageFormat,
          imageQuality, 
          buildImageCmd,
          buildImageStatus }
STATUS  current
DESCRIPTION
"<Definition> The set of TSS objects required for supporting images in 
NTCIP 1209 v03.
<Object Identifier> 1.3.6.1.4.1.1206.4.2.4.127.2.21"
::= { tssGroups 21 }

-- 5.7.22 TSS PTZ Group Version 2
tssPTZGroupV2 OBJECT-GROUP
OBJECTS { cameraDetectionState }
STATUS  current
DESCRIPTION
"<Definition> The set of TSS objects required for supporting pan, tilt, and 
zoom in NTCIP 1209 v03.
<Object Identifier> 1.3.6.1.4.1.1206.4.2.4.127.2.22"
::= { tssGroups 22 }

-- 5.7.23 TSS Core Group Version 3
tssCoreGroupV3 OBJECT-GROUP
OBJECTS { sensorSystemReset,
          sensorSystemStatus,
          sensorSystemOccupancyType,
          maxSensorZones,
          sensorZoneNumber,
          sensorZoneOptions,
          sensorZoneOptionsStatus,
          sensorZoneStatus,
          sensorZoneNoActivityFaultTime,
          sensorZoneMaxPresenceFaultTime,
          sensorZoneErraticCountsFaultTime,
          sensorZoneErraticCountsThreshold,
          sensorZoneTechnology,
          maxNumberOfCharacters,
          functionalCapabilities,
          sensorZoneOutputMode,
          tssRestartTimeMax,
          maxOutputNumber,
          outputNumber,
          outputSensorZoneNumber,
          outputLabel,
          outputFailsafeModeV3,
          outputFailsafeReset,
          outputOverrideMode,
          outputModeStatusV3,
          maxOutputGroups,
          outputGroupNumber,
          outputGroupOutputState }
STATUS  current
DESCRIPTION
"<Definition> The core set of TSS objects required for all implementations of 
NTCIP 1209 v03.
<Object Identifier> 1.3.6.1.4.1.1206.4.2.4.127.2.23"
::= { tssGroups 23 }

-- 5.7.24 TSS Arming Inputs Group Version 3
tssArmingInputsGroupV3 OBJECT-GROUP
OBJECTS { externalArmingInputsV3,
          externalArmingBitStatus }
STATUS  current
DESCRIPTION
"<Definition> The set of TSS objects required for supporting arming inputs in 
NTCIP 1209 v03.
<Object Identifier> 1.3.6.1.4.1.1206.4.2.4.127.2.24"
::= { tssGroups 24 }

-- 5.7.25 TSS Arming Outputs Group Version 3
tssArmingOutputsGroupV3 OBJECT-GROUP
OBJECTS { outputArmingEnablesV3,
          outputArmingMode }
STATUS  current
DESCRIPTION
"<Definition> The set of TSS objects required for supporting arming outputs in 
NTCIP 1209 v03.
<Object Identifier> 1.3.6.1.4.1.1206.4.2.4.127.2.25"
::= { tssGroups 25 }

-- 5.7.26 TSS Sample Group Version 3
tssSampleGroupV3 OBJECT-GROUP
OBJECTS { sensorZoneSamplePeriod, 
          maxSampleDataEntries,
          numSampleDataEntries,
          numSensorZoneClass,
          sampleEntryNum,
          sampleZoneClass,
          sampleVolumeData,
          samplePercentOccupancy,
          sampleZoneStatus,
          sampleSequenceNumber,
          zoneClassLabel,
          sampleEndTimeStamp }
STATUS  current
DESCRIPTION
"<Definition> The set of TSS objects required for TSS sample management in 
NTCIP 1209 v03.
<Object Identifier> 1.3.6.1.4.1.1206.4.2.4.127.2.26"
::= { tssGroups 26 }

-- 5.7.27 TSS Video Group Version 3
tssVideoGroupV3 OBJECT-GROUP
OBJECTS { maxCameraCount, 
          cameraNumber,
          imageReceptionDiagnostic,
          zoneListForCameraV3 }
STATUS  current
DESCRIPTION
"<Definition> The set of TSS objects required for TSS video image processing 
management in NTCIP 1209 v03.
<Object Identifier> 1.3.6.1.4.1.1206.4.2.4.127.2.27"
::= { tssGroups 27 }

END
